;;; ==========================================================================
;;; 파일명: TSP_5G_DCL_and_Strut.lsp
;;; 구  분: DCL 다이얼로그 UI, 세그먼트 매니저 및 버팀보/앵커/까치발 수동 작도 (Part G)
;;; 역  할: 전체 DCL 생성, 세그먼트 매니저/마법사/대시보드, 지반/범례/벽체/사보강재/지보재 콜백, 수동 버팀보/까치발/연속보강재/앵커편심각/중간말뚝 작도 및 제어 [draw-tsp-legend, tsp-get-abbr, tsp-format-soil-name]
;;; 포함 함수: draw-tsp-legend, tsp-get-abbr, tsp-format-soil-name
;;; --------------------------------------------------------------------------
;;; [안내] 이 파일은 TSP.lsp(메인 로더)에 의해 자동으로 로드되는 하위 모듈입니다.
;;;        코드 수정 시 전체 파일을 합칠 필요 없이 이 파일만 단독 패치하면 됩니다.
;;; ==========================================================================

;;;;==========================================================================
;;;; defun draw-tsp-legend : 지반 범례(Legend) 도면 작도
;;;;==========================================================================
(defun draw-tsp-legend (pt mode temp-layers / all-data target-data box-w text-w row-h title-h s-factor layer-name item p-name p-pat p-scale p-angle p1 p2 p3 p4 center-pt text-pt final-scale rect-pl num-items num-rows total-w i col row box-x box-y cx cy p-type abbr-name already ad base-y tri-h tri-w-half line1-len line1-start line1-end line1-mid l2-half off-y1 line2-y line2-start line2-end l3-half off-y2 line3-y line3-start line3-end tri-p1 tri-p2 tri-p3 tri-p_top_center tot-p1 tot-p2 tot-p3 tot-p4)
  (setq layer-name "_지반선")
  (setq s-factor (if *tsp-scale-section* (/ *tsp-scale-section* 200.0) 1.0))
  (setq title-h (* 2000.0 s-factor))
  (setq row-h (* 2000.0 s-factor))
  (setq box-w (* 2000.0 s-factor))
  (setq text-w (* 4000.0 s-factor))
  (setq total-w (* 12000.0 s-factor))
  (setq all-data '(
    ("입도양호 자갈(GW)" "GW_" 100.0 0.0)
    ("입도불량 자갈(GP)" "GP_" 100.0 0.0)
    ("실트질 자갈(GM)" "GM_" 100.0 0.0)
    ("점토질 자갈(GC)" "GC_" 100.0 0.0)
    ("입도양호 모래(SW)" "SW_" 100.0 0.0)
    ("입도불량 모래(SP)" "SP_" 100.0 0.0)
    ("실트질 모래(SM)" "SM_" 100.0 0.0)
    ("점토질 모래(SC)" "SC_" 100.0 0.0)
    ("저소성 실트(ML)" "ML_" 100.0 0.0)
    ("고소성 실트(MH)" "MH_" 100.0 0.0)
    ("저소성 점토(CL)" "CL_" 100.0 0.0)
    ("고소성 점토(CH)" "CH_" 100.0 0.0)
    ("전석(BOULDER)" "GRAVEL" 30.0 0.0)
    ("풍화잔류토(RS)" "RS_" 2500.0 0.0)
    ("풍화암(WR)" "WR_" 100.0 0.0)
    ("연암(SR)" "SR_" 100.0 0.0)
    ("경암(HR)" "HR_" 100.0 0.0)
    ("기타" "LINE" 78.74 0.0)
  ))
  (setq target-data '())
  (if (= (strcase mode) "USED")
    (progn
      (foreach layer temp-layers
        (setq p-type (nth 5 layer))
        (setq abbr-name (tsp-get-abbr p-type))
        (setq already nil)
        (foreach td target-data
          (if (= (car td) abbr-name) (setq already t))
        )
        (if (not already)
          (foreach ad all-data
            (if (= (car ad) p-type)
              (setq target-data (append target-data (list (list abbr-name (nth 1 ad) (nth 2 ad) (nth 3 ad)))))
            )
          )
        )
      )
      (if (= *tsp-water-chk* "1")
        (setq target-data (append target-data (list (list "지하수위" "GWL" 1.0 0.0))))
      )
    )
    (progn
      (foreach ad all-data
        ;; "전체" 모드일 때는 "기타" 지층을 범례에서 제외
        (if (/= (nth 0 ad) "기타")
          (setq target-data (append target-data (list (list (tsp-get-abbr (nth 0 ad)) (nth 1 ad) (nth 2 ad) (nth 3 ad)))))
        )
      )
      (setq target-data (append target-data (list (list "지하수위" "GWL" 1.0 0.0))))
    )
  )
  (setq num-items (length target-data))
  (setq num-rows (fix (/ (+ num-items 1) 2)))
  ;; --- 표 외곽선 및 타이틀 작도 ---
  (entmake (list '(0 . "TEXT") '(100 . "AcDbEntity") '(100 . "AcDbText") (cons 8 layer-name) (cons 62 8)
                 (cons 10 (list (+ (car pt) (/ total-w 2.0)) (- (cadr pt) (/ title-h 2.0)) 0.0))
                 (cons 40 (* 800.0 s-factor)) (cons 1 "범   례")
                 (cons 72 1) (cons 73 2) (cons 11 (list (+ (car pt) (/ total-w 2.0)) (- (cadr pt) (/ title-h 2.0)) 0.0))))
  ;; 줌 기능을 위해 전체 범례 외곽 좌표를 독립된 변수에 저장
  (setq tot-p1 (list (car pt) (cadr pt) 0.0))
  (setq tot-p2 (list (+ (car pt) total-w) (cadr pt) 0.0))
  (setq tot-p3 (list (+ (car pt) total-w) (- (cadr pt) (+ title-h (* num-rows row-h))) 0.0))
  (setq tot-p4 (list (car pt) (- (cadr pt) (+ title-h (* num-rows row-h))) 0.0))
  (entmake (list '(0 . "LWPOLYLINE") '(100 . "AcDbEntity") '(100 . "AcDbPolyline") (cons 8 layer-name) (cons 62 8) '(90 . 4) '(70 . 1)
                 (cons 10 tot-p1) (cons 10 tot-p2) (cons 10 tot-p3) (cons 10 tot-p4)))
  (entmake (list '(0 . "LINE") (cons 8 layer-name) (cons 62 8)
                 (cons 10 (list (car pt) (- (cadr pt) title-h) 0.0))
                 (cons 11 (list (+ (car pt) total-w) (- (cadr pt) title-h) 0.0))))
  (foreach vx (list box-w (+ box-w text-w) (+ box-w text-w box-w))
    (entmake (list '(0 . "LINE") (cons 8 layer-name) (cons 62 8)
                   (cons 10 (list (+ (car pt) vx) (- (cadr pt) title-h) 0.0))
                   (cons 11 (list (+ (car pt) vx) (- (cadr pt) (+ title-h (* num-rows row-h))) 0.0))))
  )
  (setq i 1)
  (while (< i num-rows)
    (entmake (list '(0 . "LINE") (cons 8 layer-name) (cons 62 8)
                   (cons 10 (list (car pt) (- (cadr pt) (+ title-h (* i row-h))) 0.0))
                   (cons 11 (list (+ (car pt) total-w) (- (cadr pt) (+ title-h (* i row-h))) 0.0))))
    (setq i (1+ i))
  )
  ;; --- 데이터 및 해치/기호 채우기 ---
  (setq i 0)
  (while (< i num-items)
    (setq item (nth i target-data))
    (setq p-name (nth 0 item) p-pat (nth 1 item) p-scale (nth 2 item) p-angle (nth 3 item))
    (setq col (/ i num-rows))
    (setq row (rem i num-rows))
    (setq box-x (+ (car pt) (* col (+ box-w text-w))))
    (setq box-y (- (cadr pt) (+ title-h (* row row-h))))
    ;; 여기서 내부 해치 박스 그리느라 p1, p2, p3, p4가 오염됨
    (setq p1 (list box-x box-y 0.0))
    (setq p2 (list (+ box-x box-w) box-y 0.0))
    (setq p3 (list (+ box-x box-w) (- box-y row-h) 0.0))
    (setq p4 (list box-x (- box-y row-h) 0.0))
    (setq center-pt (list (+ box-x (/ box-w 2.0)) (- box-y (/ row-h 2.0)) 0.0))
    (if (= p-pat "GWL")
      (progn
        (setq cx (car center-pt) cy (cadr center-pt))
        (setq base-y (- cy (* 300.0 s-factor)))
        (setq tri-h (* 800.0 s-factor))
        (setq tri-w-half (/ tri-h (sqrt 3.0)))
        (setq line1-len (* 2000.0 s-factor))
        (setq line1-start (list (- cx (/ line1-len 2.0)) base-y 0.0))
        (setq line1-end (list (+ cx (/ line1-len 2.0)) base-y 0.0))
        (setq line1-mid (list cx base-y 0.0))
        (entmake (list '(0 . "LWPOLYLINE") '(100 . "AcDbEntity") '(100 . "AcDbPolyline") (cons 8 layer-name) (cons 62 8) '(90 . 2) '(70 . 0) (cons 10 line1-start) (cons 10 line1-end)))
        (setq l2-half (* 750.0 s-factor)) (setq off-y1 (* 100.0 s-factor)) (setq line2-y (- base-y off-y1))
        (setq line2-start (list (- cx l2-half) line2-y 0.0)) (setq line2-end (list (+ cx l2-half) line2-y 0.0))
        (entmake (list '(0 . "LWPOLYLINE") '(100 . "AcDbEntity") '(100 . "AcDbPolyline") (cons 8 layer-name) (cons 62 8) '(90 . 2) '(70 . 0) (cons 10 line2-start) (cons 10 line2-end)))
        (setq l3-half (* 500.0 s-factor)) (setq off-y2 (* 200.0 s-factor)) (setq line3-y (- base-y off-y2))
        (setq line3-start (list (- cx l3-half) line3-y 0.0)) (setq line3-end (list (+ cx l3-half) line3-y 0.0))
        (entmake (list '(0 . "LWPOLYLINE") '(100 . "AcDbEntity") '(100 . "AcDbPolyline") (cons 8 layer-name) (cons 62 8) '(90 . 2) '(70 . 0) (cons 10 line3-start) (cons 10 line3-end)))
        (setq tri-p3 line1-mid)
        (setq tri-p1 (list (- cx tri-w-half) (+ base-y tri-h) 0.0))
        (setq tri-p2 (list (+ cx tri-w-half) (+ base-y tri-h) 0.0))
        (entmake (list '(0 . "LWPOLYLINE") '(100 . "AcDbEntity") '(100 . "AcDbPolyline") (cons 8 layer-name) (cons 62 8) '(90 . 3) '(70 . 1) (cons 10 tri-p1) (cons 10 tri-p2) (cons 10 tri-p3)))
        (setq tri-p_top_center (list cx (+ base-y tri-h) 0.0))
        (entmake (list '(0 . "SOLID") '(100 . "AcDbEntity") '(100 . "AcDbTrace") (cons 8 layer-name) (cons 62 8) (cons 10 tri-p1) (cons 11 tri-p_top_center) (cons 12 tri-p3) (cons 13 tri-p3)))
      )
      (progn
        (entmake (list '(0 . "LWPOLYLINE") '(100 . "AcDbEntity") '(100 . "AcDbPolyline") (cons 8 layer-name) (cons 62 8) '(90 . 4) '(70 . 1)
                       (cons 10 p1) (cons 10 p2) (cons 10 p3) (cons 10 p4)))
        (setq rect-pl (entlast))
        (setq final-scale (* p-scale s-factor 2.0))
        (if rect-pl
          (tsp-apply-custom-hatch rect-pl p-pat final-scale (* p-angle (/ pi 180.0)) layer-name 8 center-pt)
        )
      )
    )
    (setq text-pt (list (+ box-x box-w (/ text-w 2.0)) (- box-y (/ row-h 2.0)) 0.0))
    (entmake (list '(0 . "TEXT") '(100 . "AcDbEntity") '(100 . "AcDbText") (cons 8 layer-name) (cons 62 8)
                   (cons 10 text-pt) (cons 40 (* 600.0 s-factor)) (cons 1 p-name)
                   (cons 72 1) (cons 73 2) (cons 11 text-pt)))
    (setq i (1+ i))
  )
  (princ "\n범례 생성 완료.")
  (list tot-p1 tot-p2 tot-p3 tot-p4)
)

;;; --------------------------------------------------------------------------
;;; Function: tsp-get-abbr, tsp-format-soil-name
;;; Description: 지층명칭 추출 및 변환
;;; --------------------------------------------------------------------------
(defun tsp-get-abbr (str / p1 p2 res)
  (setq p1 (vl-string-search "(" str))
  (setq p2 (vl-string-search ")" str))
  (if (and p1 p2 (> p2 p1))
    (setq res (substr str (+ p1 2) (- p2 p1 1)))
    (setq res str)
  )
  (if (= res "BOULDER") (setq res "BO"))
  res
)

(defun tsp-format-soil-name (str / p1 base-str)
  (setq p1 (vl-string-search "(" str))
  (if p1
    (setq base-str (substr str 1 p1))
    (setq base-str str)
  )
  (while (and (> (strlen base-str) 0) (= (substr base-str (strlen base-str) 1) " "))
    (setq base-str (substr base-str 1 (1- (strlen base-str))))
  )
  (while (vl-string-search "저소성" base-str)
    (setq base-str (vl-string-subst "압축성 낮은" "저소성" base-str))
  )
  (while (vl-string-search "고소성" base-str)
    (setq base-str (vl-string-subst "압축성 높은" "고소성" base-str))
  )
  base-str
)
