;;; ==========================================================================
;;; 파일명: TSP_1A_Globals_Utils.lsp
;;; 구  분: 전역 변수 및 공통/그룹 유틸리티 (Part A)
;;; 역  할: 해치 패턴(16종), 표준 H형강 규격, 전역 설정 변수, 레이어/해치 유틸리티, 프로젝트 저장/불러오기/자동매칭, 도면 그룹(ACAD_GROUP) 제어 [get-hatch-scale-factor, create-layer-if-not-exists, is-numeric, parse-h-spec, format-depth-text 외 5개]
;;; 포함 함수: get-hatch-scale-factor, create-layer-if-not-exists, is-numeric, parse-h-spec, format-depth-text, tsp-sanitize-project-name, tsp-get-project-list, tsp-generate-default-project-name, tsp-save-project-data, tsp-shape-mismatch-prompt
;;; --------------------------------------------------------------------------
;;; [안내] 이 파일은 TSP.lsp(메인 로더)에 의해 자동으로 로드되는 하위 모듈입니다.
;;;        코드 수정 시 전체 파일을 합칠 필요 없이 이 파일만 단독 패치하면 됩니다.
;;; ==========================================================================

;;; ==========================================================================
;;; TSP.lsp - Temporary Structure Plan (Integrated Version)
;;; ==========================================================================
(vl-load-com)
;;; ==========================================================================
;;; [SECTION 1] 전역 변수 및 설정 (Global Variables)
;;; ==========================================================================
;;; ==========================================================================
;;; [교체 변수] 사용자 정의 지층 해치 패턴(PAT) 데이터베이스 (총 16종)
;;; ==========================================================================
(setq *tsp-custom-pat-data*
  '(
    ("CH_"
     "*CH_, 압축성 높은 점토"
     "45,0,0,0,3.53553391"
     "45,0.4,0,0,3.53553391"
    )
    ("CL_"
     "*CL_, 압축성 낮은 점토"
     "45,0,0,0,3.53553391"
    )
    ("GC_"
     "*GC_, 점토질 자갈"
     "45,0,0,0,3.53553391"
     "0,-0.21,0.72,2.5,2.5,0.42,-4.58"
     "0,-0.45,0.6,2.5,2.5,0.9,-4.1"
     "0,-0.5763,0.48,2.5,2.5,1.1526,-3.8474"
     "0,-0.658,0.36,2.5,2.5,1.3159,-3.6841"
     "0,-0.7106,0.24,2.5,2.5,1.4211,-3.5789"
     "0,-0.7403,0.12,2.5,2.5,1.4807,-3.5193"
     "0,-0.75,0,2.5,2.5,1.5,-3.5"
     "0,-0.7403,-0.12,2.5,2.5,1.4807,-3.5193"
     "0,-0.7106,-0.24,2.5,2.5,1.4211,-3.5789"
     "0,-0.658,-0.36,2.5,2.5,1.3159,-3.6841"
     "0,-0.5763,-0.48,2.5,2.5,1.1526,-3.8474"
     "0,-0.45,-0.6,2.5,2.5,0.9,-4.1"
     "0,-0.21,-0.72,2.5,2.5,0.42,-4.58"
    )
    ("GM_"
     "*GM_, 실트질 자갈"
     "90,0,0,0,2.5"
     "0,-0.21,0.72,2.5,2.5,0.42,-4.58"
     "0,-0.45,0.6,2.5,2.5,0.9,-4.1"
     "0,-0.5763,0.48,2.5,2.5,1.1526,-3.8474"
     "0,-0.658,0.36,2.5,2.5,1.3159,-3.6841"
     "0,-0.7106,0.24,2.5,2.5,1.4211,-3.5789"
     "0,-0.7403,0.12,2.5,2.5,1.4807,-3.5193"
     "0,-0.75,0,2.5,2.5,1.5,-3.5"
     "0,-0.7403,-0.12,2.5,2.5,1.4807,-3.5193"
     "0,-0.7106,-0.24,2.5,2.5,1.4211,-3.5789"
     "0,-0.658,-0.36,2.5,2.5,1.3159,-3.6841"
     "0,-0.5763,-0.48,2.5,2.5,1.1526,-3.8474"
     "0,-0.45,-0.6,2.5,2.5,0.9,-4.1"
     "0,-0.21,-0.72,2.5,2.5,0.42,-4.58"
    )
    ("GP_"
     "*GP_, 입도 불량 자갈"
     "0,0,0,2.5,2.5,0.42,-4.58"
     "0,-0.24,-0.12,2.5,2.5,0.9,-4.1"
     "0,-0.3663,-0.24,2.5,2.5,1.1526,-3.8474"
     "0,-0.448,-0.36,2.5,2.5,1.3159,-3.6841"
     "0,-0.5006,-0.48,2.5,2.5,1.4211,-3.5789"
     "0,-0.5303,-0.6,2.5,2.5,1.4807,-3.5193"
     "0,-0.54,-0.72,2.5,2.5,1.5,-3.5"
     "0,-0.5303,-0.84,2.5,2.5,1.4807,-3.5193"
     "0,-0.5006,-0.96,2.5,2.5,1.4211,-3.5789"
     "0,-0.448,-1.08,2.5,2.5,1.3159,-3.6841"
     "0,-0.3663,-1.2,2.5,2.5,1.1526,-3.8474"
     "0,-0.24,-1.32,2.5,2.5,0.9,-4.1"
     "0,0,-1.44,2.5,2.5,0.42,-4.58"
     "63.43494882,2.91,4.08,4.47213596,2.23606798,0.2236068,-10.95673309"
     "26.56505118,2.71,3.98,6.70820393,2.23606798,0.2236068,-10.95673309"
     "333.43494882,2.51,4.08,4.47213596,2.23606798,0.2236068,-10.95673309"
     "296.56505118,2.41,4.28,6.70820393,2.23606797,0.2236068,-10.95673309"
     "153.43494882,0.41,1.98,4.47213595,2.23606797,0.2236068,-10.95673309"
     "116.56505118,0.51,1.78,6.70820393,2.23606798,0.2236068,-10.95673309"
     "63.43494882,0.41,1.58,4.47213596,2.23606798,0.2236068,-10.95673309"
     "26.56505118,0.21,1.48,6.70820393,2.23606798,0.2236068,-10.95673309"
     "243.43494882,2.51,-0.52,4.47213596,2.23606798,0.2236068,-10.95673309"
     "206.56505118,2.71,-0.42,6.70820393,2.23606797,0.2236068,-10.95673309"
     "153.43494882,2.91,-0.52,4.47213595,2.23606797,0.2236068,-10.95673309"
     "116.56505118,3.01,-0.72,6.70820393,2.23606798,0.2236068,-10.95673309"
     "333.43494882,5.01,1.58,4.47213596,2.23606798,0.2236068,-10.95673309"
     "296.56505118,4.91,1.78,6.70820393,2.23606797,0.2236068,-10.95673309"
     "243.43494882,5.01,1.98,4.47213596,2.23606798,0.2236068,-10.95673309"
     "206.56505118,5.21,2.08,6.70820393,2.23606797,0.2236068,-10.95673309"
    )
    ("GW_"
     "*GW_, 입도 양호 자갈"
     "189.46232221,0,0,25.48184303,0.82199494,0.30413812,-30.10967452"
     "210.96375653,-0.3,-0.05,18.00735144,0.85749293,0.2915476,-28.86321188"
     "239.03624347,-0.55,-0.2,11.14740804,0.85749292,0.2915476,-28.86321188"
     "260.53767779,-0.7,-0.45,4.93196962,0.82199494,0.30413813,-30.10967453"
     "279.46232221,-0.75,-0.75,25.48184303,0.82199494,0.30413812,-30.10967452"
     "300.96375653,-0.7,-1.05,18.00735144,0.85749292,0.2915476,-28.86321188"
     "329.03624347,-0.55,-1.3,11.14740804,0.85749292,0.2915476,-28.86321188"
     "350.53767779,-0.3,-1.45,4.93196962,0.82199493,0.30413813,-30.10967453"
     "9.46232221,0,-1.5,25.48184303,0.82199494,0.30413812,-30.10967452"
     "30.96375653,0.3,-1.45,18.00735144,0.85749293,0.29154759,-28.86321188"
     "59.03624347,0.55,-1.3,11.14740804,0.85749292,0.2915476,-28.86321188"
     "80.53767779,0.7,-1.05,4.93196962,0.82199494,0.30413812,-30.10967452"
     "99.46232221,0.75,-0.75,25.48184303,0.82199494,0.30413812,-30.10967452"
     "120.96375653,0.7,-0.45,18.00735144,0.85749292,0.2915476,-28.86321188"
     "149.03624347,0.55,-0.2,11.14740804,0.85749292,0.2915476,-28.86321188"
     "170.53767779,0.3,-0.05,4.93196962,0.82199493,0.30413812,-30.10967452"
     "99.46232221,-1.75,-3.25,25.48184303,0.82199494,0.30413812,-30.10967452"
     "120.96375653,-1.8,-2.95,18.00735144,0.85749292,0.2915476,-28.86321188"
     "149.03624347,-1.95,-2.7,11.14740804,0.85749292,0.2915476,-28.86321188"
     "170.53767779,-2.2,-2.55,4.93196962,0.82199493,0.30413812,-30.10967452"
     "9.46232221,-2.5,1,25.48184303,0.82199494,0.30413812,-30.10967452"
     "30.96375653,-2.2,1.05,18.00735144,0.85749293,0.29154759,-28.86321188"
     "59.03624347,-1.95,1.2,11.14740804,0.85749292,0.2915476,-28.86321188"
     "80.53767779,-1.8,1.45,4.93196962,0.82199494,0.30413812,-30.10967452"
     "279.46232221,1.75,1.75,25.48184303,0.82199494,0.30413812,-30.10967452"
     "300.96375653,1.8,1.45,18.00735144,0.85749292,0.2915476,-28.86321188"
     "329.03624347,1.95,1.2,11.14740804,0.85749292,0.2915476,-28.86321188"
     "350.53767779,2.2,1.05,4.93196962,0.82199493,0.30413813,-30.10967453"
     "189.46232221,2.5,-2.5,25.48184303,0.82199494,0.30413812,-30.10967452"
     "210.96375653,2.2,-2.55,18.00735144,0.85749293,0.2915476,-28.86321188"
     "239.03624347,1.95,-2.7,11.14740804,0.85749292,0.2915476,-28.86321188"
     "260.53767779,1.8,-2.95,4.93196962,0.82199494,0.30413813,-30.10967453"
     "63.43494882,0.2,1.55,4.47213596,2.23606798,0.2236068,-10.95673309"
     "26.56505118,0,1.45,6.70820393,2.23606798,0.2236068,-10.95673309"
     "333.43494882,-0.2,1.55,4.47213596,2.23606798,0.2236068,-10.95673309"
     "296.56505118,-0.3,1.75,6.70820393,2.23606797,0.2236068,-10.95673309"
     "153.43494882,-2.3,-0.55,4.47213595,2.23606797,0.2236068,-10.95673309"
     "116.56505118,-2.2,-0.75,6.70820393,2.23606798,0.2236068,-10.95673309"
     "63.43494882,-2.3,-0.95,4.47213596,2.23606798,0.2236068,-10.95673309"
     "26.56505118,-2.5,-1.05,6.70820393,2.23606798,0.2236068,-10.95673309"
     "243.43494882,-0.2,-3.05,4.47213596,2.23606798,0.2236068,-10.95673309"
     "206.56505118,0,-2.95,6.70820393,2.23606797,0.2236068,-10.95673309"
     "153.43494882,0.2,-3.05,4.47213595,2.23606797,0.2236068,-10.95673309"
     "116.56505118,0.3,-3.25,6.70820393,2.23606798,0.2236068,-10.95673309"
     "333.43494882,2.3,-0.95,4.47213596,2.23606798,0.2236068,-10.95673309"
     "296.56505118,2.2,-0.75,6.70820393,2.23606797,0.2236068,-10.95673309"
     "243.43494882,2.3,-0.55,4.47213596,2.23606798,0.2236068,-10.95673309"
     "206.56505118,2.5,-0.45,6.70820393,2.23606797,0.2236068,-10.95673309"
    )
    ("HR_"
     "*HR_, 경암"
     "0,0,0,2.5,2.5,1.5,-3.5"
     "90,0.75,-0.75,2.5,2.5,1.5,-3.5"
    )
    ("MH_"
     "*MH_, 압축성 높은 실트"
     "90,0,0,0,2.5"
     "90,0.4,0,0,2.5"
    )
    ("ML_"
     "*ML_, 압축성 낮은 실트"
     "90,0,0,0,2.5"
    )
    ("RS_"
     "*RS_, 풍화토"
     "45,0,0,0.1767767,0.1767767"
     "45,0.01414,-0.01414,0.1767767,0.1767767"
     "0,0.0175,0.1725,0.125,0.125,0.06,-0.19"
     "90,0.0475,0.1425,0.125,0.125,0.06,-0.19"
     "45,-0.01415,0.01414,0.1767767,0.1767767"
    )
    ("SC_"
     "*SC_, 점토질 모래"
     "45,0,0,0,3.53553391"
     "0,-0.2062,0.4,2.5,2.5,0.4123,-4.5877"
     "0,-0.3354,0.3,2.5,2.5,0.6708,-4.3292"
     "0,-0.4031,0.2,2.5,2.5,0.8062,-4.1938"
     "0,-0.4387,0.1,2.5,2.5,0.8775,-4.1225"
     "0,-0.45,0,2.5,2.5,0.9,-4.1"
     "0,-0.4387,-0.1,2.5,2.5,0.8775,-4.1225"
     "0,-0.4031,-0.2,2.5,2.5,0.8062,-4.1938"
     "0,-0.3354,-0.3,2.5,2.5,0.6708,-4.3292"
     "0,-0.2062,-0.4,2.5,2.5,0.4123,-4.5877"
    )
    ("SM_"
     "*SM_, 실트질 모래"
     "90,0,0,0,2.5"
     "0,-0.2062,0.4,2.5,2.5,0.4123,-4.5877"
     "0,-0.3354,0.3,2.5,2.5,0.6708,-4.3292"
     "0,-0.4031,0.2,2.5,2.5,0.8062,-4.1938"
     "0,-0.4387,0.1,2.5,2.5,0.8775,-4.1225"
     "0,-0.45,0,2.5,2.5,0.9,-4.1"
     "0,-0.4387,-0.1,2.5,2.5,0.8775,-4.1225"
     "0,-0.4031,-0.2,2.5,2.5,0.8062,-4.1938"
     "0,-0.3354,-0.3,2.5,2.5,0.6708,-4.3292"
     "0,-0.2062,-0.4,2.5,2.5,0.4123,-4.5877"
    )
    ("SP_"
     "*SP_, 입도 불량 모래"
     "0,0,0,2.5,2.5,0.4123,-4.5877"
     "0,-0.1292,-0.1,2.5,2.5,0.6708,-4.3292"
     "0,-0.1969,-0.2,2.5,2.5,0.8062,-4.1938"
     "0,-0.2325,-0.3,2.5,2.5,0.8775,-4.1225"
     "0,-0.2438,-0.4,2.5,2.5,0.9,-4.1"
     "0,-0.2325,-0.5,2.5,2.5,0.8775,-4.1225"
     "0,-0.1969,-0.6,2.5,2.5,0.8062,-4.1938"
     "0,-0.1292,-0.7,2.5,2.5,0.6708,-4.3292"
     "0,0,-0.8,2.5,2.5,0.4123,-4.5877"
    )
    ("SR_"
     "*SR_, 연암"
     "0,0,0,2.5,2.5,1.5,-3.5"
     "90,0.75,-0.75,2.5,2.5,1.5,-3.5"
     "45,-1.75,0,0,3.53553391"
    )
    ("SW_"
     "*SW_, 입도 양호 모래"
     "206.56505118,0,0,6.70820393,2.23606797,0.3354102,-10.84492969"
     "153.43494882,0.3,-0.15,4.47213595,2.23606797,0.3354102,-10.84492969"
     "116.56505118,0.45,-0.45,6.70820393,2.23606798,0.3354102,-10.84492969"
     "63.43494882,0.3,-0.75,4.47213596,2.23606798,0.33541019,-10.84492969"
     "26.56505118,0,-0.9,6.70820393,2.23606798,0.3354102,-10.84492969"
     "333.43494882,-0.3,-0.75,4.47213596,2.23606798,0.3354102,-10.84492969"
     "296.56505118,-0.45,-0.45,6.70820393,2.23606797,0.3354102,-10.84492969"
     "243.43494882,-0.3,-0.15,4.47213596,2.23606798,0.3354102,-10.84492969"
     "153.43494882,-2.2,-2.65,4.47213595,2.23606797,0.3354102,-10.84492969"
     "116.56505118,-2.05,-2.95,6.70820393,2.23606798,0.3354102,-10.84492969"
     "63.43494882,-2.2,1.75,4.47213596,2.23606798,0.33541019,-10.84492969"
     "26.56505118,-2.5,1.6,6.70820393,2.23606798,0.3354102,-10.84492969"
     "333.43494882,2.2,1.75,4.47213596,2.23606798,0.3354102,-10.84492969"
     "296.56505118,2.05,2.05,6.70820393,2.23606797,0.3354102,-10.84492969"
     "243.43494882,2.2,-2.65,4.47213596,2.23606798,0.3354102,-10.84492969"
     "206.56505118,2.5,-2.5,6.70820393,2.23606797,0.3354102,-10.84492969"
    )
    ("WR_"
     "*WR_, 풍화암"
     "0,0,0,2.5,2.5,1.5,-3.5"
     "90,0.75,-0.75,2.5,2.5,1.5,-3.5"
     "45,-1.95,0,0,3.53553391"
     "45,-1.55,0,0,3.53553391"
    )
  )
)
;;; 표준 규격 리스트 중앙 관리
(setq *tsp-std-wall-list* '(
  "H 250×250×9/14"      ; 0
  "H 298×201×9/14"      ; 1
  "H 300×300×10/15"    ; 2
  "H 350×350×12/19"
  "H 400×400×13/21"
))
(setq *tsp-std-strut-list* '(
  "H 250×250×9/14"
  "H 298×201×9/14"
  "H 300×300×10/15"
  "H 350×350×12/19"
  "H 400×400×13/21"
))
;;; 1.1 H-Pile 및 띠장(Wale) 규격 변수
;;; (기본값 설정: 리스트의 인덱스를 사용하여 안전하게 가져옴)
(setq *tsp-hpile-spec* (nth 2 *tsp-std-wall-list*))     ; 기본값: H 300
(setq *tsp-hpile-custom* '(300 300 10 15))
(setq *tsp-wale-spec* (nth 2 *tsp-std-wall-list*))      ; 기본값: H 300
(setq *tsp-wale-custom* '(300 300 10 15))
;; 1.14 벽체 공법 타입 변수
;; [1단계 고정] 기본값은 항상 "HPILE", C.I.P는 사용자가 최종 확정 시에만 "CIP"로 변경됨
(setq *tsp-wall-type* "HPILE")      ; 벽체 공법 타입 기본값 ("HPILE" or "CIP")
;; 1.15 C.I.P 흙막이벽 전용 설정 변수
(setq *tsp-cip-max-depth* "10.0")   ; 최대 굴착 깊이
(setq *tsp-cip-embed-depth* "3.0")  ; 근입 깊이
(setq *tsp-cip-hpile-idx* "2")      ; H-Pile 규격 인덱스 (기본값: H 300)
(setq *tsp-cip-wale-idx* "2")       ; 띠장(Wale) 규격 인덱스 (기본값: H 300)
(setq *tsp-cip-dia* "500")          ; C.I.P 직경 기본값 (D500)
(setq *tsp-cip-mode-idx* "0")       ; 배열 모드 (0: 맞닿음/Tangent, 1: 겹침/Secant)
(setq *tsp-cip-overlap* "0")        ; 겹침량 기본값
(setq *tsp-cip-interval-idx* "2")   ; H-Pile 삽입 간격 (0: 1/1, 1: 1/2, 2: 2공건너 삽입)
(setq *tsp-cip-grouting-idx* "0")   ; 그라우팅 규격 선택 (0: D200, 1: D600, 2: 없음)
;; 그라우팅 간격/기준선 옵션 및 커스텀 입력 변수 (CIP 및 H-Pile+토류판 공용)
(setq *tsp-cip-grouting-space-idx* "0")    ; 그라우팅 간격 (0: 200, 1: 400, 2: 600, 3: 직접입력)
(setq *tsp-cip-grouting-space-custom* "")  ; 직접 입력한 그라우팅 간격 값(mm)
(setq *tsp-cip-grouting-offset-idx* "0")   ; 그라우팅 기준선 (0: 기본값, 1: 직접입력, 2: 말뚝배면 H)
(setq *tsp-cip-grouting-offset-custom* "") ; 직접 입력한 그라우팅 기준선 오프셋 값(mm)
;;; 1.2 배치 및 굴착 설정 변수
(setq *tsp-ctc* 2.0)                                ; C.T.C 간격 (m)
(setq *tsp-timber-thickness* 60)                ; 토류판 두께 (mm)
(setq *tsp-max-excavation-depth* 10.0)       ; 최대 굴착 깊이 (m)
(setq *tsp-embedment-depth* 3.0)             ; 근입 깊이 (m)
;;; 1.3 지반 및 수위 변수
;;; 저장 형식: (이름 깊이 해치패턴 해치축척 해치각도 종류명 내부마찰각)
(setq *tsp-soil-layers* '())
(setq *tsp-water-chk* "0")                   ; 지하수위 체크 여부 ("0"=Off, "1"=On)
(setq *tsp-water-depth* 0.0)                 ; 지하수위 깊이 (m)
(setq *tsp-shotcrete-enable* "1")            ; 숏크리트 생성 마스터 스위치 ("0"=Off, "1"=On)
(setq *tsp-shotcrete-chk* "0")               ; 숏크리트 암반 선택 여부 ("0"=Off, "1"=On)
(setq *tsp-shotcrete-layer* "")              ; 숏크리트 시작 지정 암반층 이름
(setq *tsp-shotcrete-thick* 0.0)             ; 숏크리트 두께 T(mm)
;;; 1.4 지보재 변수
(setq *tsp-support-list* '())
;;; 1.5 도면 스케일 변수
(setq *tsp-scale-section* 200)               ; 단면도 스케일 (기본 1/200)
(setq *tsp-scale-plan* 600)                  ; 평면도 스케일 (기본 1/600)
;;; 1.6 프로젝트 관리 변수
(setq *tsp-current-project-name* "")         ; 현재 프로젝트 이름
(setq *tsp-data-dict-name* "TSP_DATA_DICT")  ; 딕셔너리 저장소 이름
;;; 1.7 변경 사항 감지 플래그
(setq *tsp-data-dirty* nil)                  ; 데이터 변경 여부 (T=변경됨, nil=변경없음)

;;; ==========================================================================
;;; [SECTION 2] 공통 유틸리티 (Common Utilities)
;;; ==========================================================================

;;;;==========================================================================
;;;; defun get-hatch-scale-factor : 도면의 MEASUREMENT 변수(0=Imperial, 1=Metric)에 따라 해치 스케일 보정값 반환
;;;;==========================================================================
(defun get-hatch-scale-factor ()
  (if (= (getvar "MEASUREMENT") 0)
    25.4  ;; Imperial 도면이면 25.4배 확대 (mm 단위처럼 보이게 보정)
    1.0   ;; Metric 도면이면 그대로 사용
  )
)

;;;;==========================================================================
;;;; defun create-layer-if-not-exists : 레이어가 존재하지 않으면 지정된 색상으로 생성
;;;;==========================================================================
(defun create-layer-if-not-exists (layer-name color / color-int)
  (if (not (tblsearch "LAYER" layer-name))
    (progn
      ;; 전달받은 color가 문자열일 경우 정수로 변환 (entmake DXF 62번은 정수만 허용)
      (setq color-int (if (= (type color) 'STR) (atoi color) color))
      (vl-catch-all-apply
        'entmake
        (list
          (list
            '(0 . "LAYER")
            '(100 . "AcDbSymbolTableRecord")
            '(100 . "AcDbLayerTableRecord")
            (cons 2 layer-name)
            '(70 . 0)
            (cons 62 color-int)
          )
        )
      )
    )
  )
)

;;;;==========================================================================
;;;; defun is-numeric : 문자열이 숫자로 변환 가능한지 확인 (True/False)
;;;;==========================================================================
(defun is-numeric (str / result)
  (setq result T)
  (if (or (null str) (= str ""))
    (setq result nil)
    (if (not (numberp (read str)))
      (setq result nil)
    )
  )
  result
)

;;;;==========================================================================
;;;; defun parse-h-spec : "H 298x201..." 형식의 문자열을 파싱하여 리스트 (298 201...)로 변환
;;;;==========================================================================
(defun parse-h-spec (spec-str / clean-str i ch result-str)
  (if (and spec-str (wcmatch spec-str "H *"))
    (progn
      (setq clean-str (substr spec-str 3))
      (setq result-str "")
      (setq i 1)
      (while (<= i (strlen clean-str))
        (setq ch (substr clean-str i 1))
        (cond
          ((and (>= (ascii ch) 48) (<= (ascii ch) 57))
           (setq result-str (strcat result-str ch)))
          (t
           (if (> (strlen result-str) 0)
             (if (/= (substr result-str (strlen result-str) 1) " ")
               (setq result-str (strcat result-str " "))
             )
           ))
        )
        (setq i (1+ i))
      )
      (read (strcat "(" result-str ")"))
    )
    nil
  )
)

;;;;==========================================================================
;;;; defun format-depth-text : 깊이 값을 소수점 1자리 문자열로 포맷팅 (ex: "5.0")
;;;;==========================================================================
(defun format-depth-text (depth / str)
  (setq str (rtos depth 2 1))
  (if (not (vl-string-search "." str))
    (setq str (strcat str ".0"))
  )
  str
)

;;;;==========================================================================
;;;; defun tsp-sanitize-project-name : 파일명 및 CSV에 사용할 수 없는 특수문자를 언더바(_)로 치환
;;;;==========================================================================
(defun tsp-sanitize-project-name (name / bad-chars i ch result)
  (setq name (if (or (= name "") (= name nil)) "Project" name))
  (setq bad-chars ",\\;:\\/\\*\\?\\\"<>|'")
  (setq result "")
  (setq i 1)
  (while (<= i (strlen name))
    (setq ch (substr name i 1))
    (if (vl-string-search ch bad-chars)
      (setq result (strcat result "_"))
      (setq result (strcat result ch))
    )
    (setq i (1+ i))
  )
  ;; 길이 제한(Windows 255자) 안전망
  (if (> (strlen result) 200) (setq result (substr result 1 200)))
  result
)

;;;;==========================================================================
;;;; defun tsp-get-project-list : 저장된 프로젝트 목록 반환 (직접 순회 방식)
;;;;==========================================================================
(defun tsp-get-project-list (/ proj-list dict-name raw-data item key)
  (setq dict-name "TSP_DATA_DICT")
  (setq proj-list '())
  ;; 1. 딕셔너리의 전체 데이터를 리스트로 가져옴
  (setq raw-data (vlax-ldata-list dict-name))
  ;; 2. 데이터가 존재하면 키(Project Name)만 추출
  (if raw-data
    (foreach item raw-data
      (setq key (car item)) ; dotted pair의 앞부분(key) 추출
      (if (= (type key) 'STR) ; 키가 문자열인 경우만 추가
        (setq proj-list (append proj-list (list key)))
      )
    )
  )
  proj-list
)

;;;;==========================================================================
;;;; defun tsp-generate-default-project-name : 중복되지 않는 다음 프로젝트 이름 생성 (Project_N+1)
;;;;==========================================================================
(defun tsp-generate-default-project-name (/ proj-list max-num curr-num name upper-name)
  (setq proj-list (tsp-get-project-list))
  (setq max-num 0)
  ;; 기존 목록에서 번호 파싱
  (foreach name proj-list
    (setq upper-name (strcase name))
    ;; "PROJECT_" 로 시작하는지 확인 (와일드카드 매칭)
    (if (wcmatch upper-name "PROJECT_*")
      (progn
        ;; "PROJECT_" 글자수(8) 다음부터 숫자 추출
        ;; 문자열이 "PROJECT_10" 이면 substr 9부터가 "10"
        (setq curr-num (atoi (substr upper-name 9)))
        (if (> curr-num max-num) (setq max-num curr-num))
      )
    )
  )
  ;; 가장 큰 번호 + 1 반환
  (strcat "Project_" (itoa (1+ max-num)))
)

;;;;==========================================================================
;;;; defun tsp-find-project-boundary-ent : 프로젝트명 및 세그먼트 좌표와 일치하는 도면 내 경계선 폴리라인 탐색
;;;;   (메인 메뉴에서 바로 [CSV 내보내기]를 실행해 *tsp-boundary-ent*가 nil인 경우에도 원본 경계선 정점을 확보)
;;;;==========================================================================
(defun tsp-find-project-boundary-ent (proj-name seg-list / bnd-ent ss i ent tagged-name p-start p-end verts match-start match-end v)
  (cond
    ;; 1순위: 현재 활성화된 *tsp-boundary-ent*가 유효하고 첫 세그먼트 시작점과 부합하는 경우
    ((and (boundp '*tsp-boundary-ent*) *tsp-boundary-ent* (entget *tsp-boundary-ent*))
     (setq bnd-ent *tsp-boundary-ent*)
     (if (and seg-list (cdr (assoc 'V-START (car seg-list))))
       (progn
         (setq p-start (cdr (assoc 'V-START (car seg-list))))
         (setq verts (extract-vertices bnd-ent))
         (setq match-start nil)
         (foreach v verts
           (if (< (distance (list (car v) (cadr v)) (list (car p-start) (cadr p-start))) 10.0)
             (setq match-start T)
           )
         )
         (if (not match-start) (setq bnd-ent nil))
       )
     )
    )
  )
  ;; 2순위: 도면 내 LWPOLYLINE 중 TSP_PROJ_NAME LDATA가 proj-name과 일치하는 경계선 탐색
  (if (and (null bnd-ent) proj-name (/= proj-name ""))
    (progn
      (setq ss (ssget "X" '((0 . "LWPOLYLINE"))))
      (if ss
        (progn
          (setq i 0)
          (while (and (< i (sslength ss)) (null bnd-ent))
            (setq ent (ssname ss i))
            (setq tagged-name (vlax-ldata-get ent "TSP_PROJ_NAME"))
            (if (and tagged-name (= (strcase tagged-name) (strcase proj-name)))
              (setq bnd-ent ent)
            )
            (setq i (1+ i))
          )
        )
      )
    )
  )
  ;; 3순위: 세그먼트 시작점(V-START)과 끝점(V-END)을 모두 정점으로 포함하는 LWPOLYLINE 탐색
  (if (and (null bnd-ent) seg-list (cdr (assoc 'V-START (car seg-list))))
    (progn
      (setq p-start (cdr (assoc 'V-START (car seg-list))))
      (setq p-end (cdr (assoc 'V-END (last seg-list))))
      (setq ss (ssget "X" '((0 . "LWPOLYLINE"))))
      (if ss
        (progn
          (setq i 0)
          (while (and (< i (sslength ss)) (null bnd-ent))
            (setq ent (ssname ss i))
            (setq verts (extract-vertices ent))
            (setq match-start nil match-end nil)
            (foreach v verts
              (if (< (distance (list (car v) (cadr v)) (list (car p-start) (cadr p-start))) 5.0)
                (setq match-start T)
              )
              (if (and p-end (< (distance (list (car v) (cadr v)) (list (car p-end) (cadr p-end))) 5.0))
                (setq match-end T)
              )
            )
            (if (and match-start match-end (>= (length verts) (length seg-list)))
              (setq bnd-ent ent)
            )
            (setq i (1+ i))
          )
        )
      )
    )
  )
  bnd-ent
)

;;;;==========================================================================
;;;; defun tsp-save-project-data : 프로젝트 데이터 저장 (원본 경계선 정점 포함)
;;;;==========================================================================
(defun tsp-save-project-data (proj-name / data-pack dict-name old-pack bnd-ent bnd-info)
  (setq dict-name "TSP_DATA_DICT")

  ;; 입력된 이름이 없으면 자동 생성, 이름이 있다면 특수문자 필터링(Sanitize) 적용
  (if (or (= proj-name "") (= proj-name nil))
    (setq proj-name (tsp-generate-default-project-name))
    (setq proj-name (tsp-sanitize-project-name proj-name))
  )

  ;; 원본 경계선 정점 정보 확보 (1순위: 도면 경계선 폴리라인, 2순위: CSV에서 로드된 경계선 데이터, 3순위: 기존 저장 데이터)
  (setq bnd-ent (tsp-find-project-boundary-ent proj-name *segment-list*))
  (setq old-pack (vlax-ldata-get dict-name proj-name))
  (setq bnd-info
    (cond
      ((and bnd-ent (entget bnd-ent))
       (list (if (is-closed-polyline bnd-ent) 1 0) (extract-vertices bnd-ent))
      )
      ((and (boundp '*tsp-csv-boundary-data*) *tsp-csv-boundary-data* (nth 1 *tsp-csv-boundary-data*))
       *tsp-csv-boundary-data*
      )
      ((and old-pack (> (length old-pack) 19) (nth 19 old-pack))
       (nth 19 old-pack)
      )
      (t nil)
    )
  )

  ;; 저장할 데이터 패키징
  (setq data-pack (list
        *segment-list*
        *tsp-hpile-spec*
        *tsp-hpile-custom*
        *tsp-wale-spec*
        *tsp-wale-custom*
        *tsp-ctc*
        *tsp-timber-thickness*
        *tsp-max-excavation-depth*
        *tsp-embedment-depth*
        *tsp-soil-layers*
        *tsp-water-chk*
        *tsp-water-depth*
        *tsp-support-list*
        *tsp-scale-section*
        *tsp-scale-plan*
        (if (vlax-ldata-get "TSP_DICT" "DELETED_POSTS") (vlax-ldata-get "TSP_DICT" "DELETED_POSTS") '())
        (if (vlax-ldata-get "TSP_DICT" "ADDED_POSTS") (vlax-ldata-get "TSP_DICT" "ADDED_POSTS") '())
        (cond
          ((and (boundp '*tsp-boundary-orient*) *tsp-boundary-orient*) *tsp-boundary-orient*)
          ((and (boundp '*tsp-imported-orient*) *tsp-imported-orient*) *tsp-imported-orient*)
          (t 1)
        )
        ;; [까치발 삭제] 19번째(인덱스 18): 사용자가 삭제한 까치발 목록
        (if (vlax-ldata-get "TSP_DICT" "DELETED_CORBELS") (vlax-ldata-get "TSP_DICT" "DELETED_CORBELS") '())
        ;; [경계선 원본 보존] 20번째(인덱스 19): (폐합여부 ((x1 y1 0.0) (x2 y2 0.0) ...))
        bnd-info
      ))
  ;; ldata에 저장 수행
  (vlax-ldata-put dict-name proj-name data-pack)
  (setq *tsp-current-project-name* proj-name)
  (princ (strcat "\n[시스템] 프로젝트 '" proj-name "' 이(가) 도면에 저장되었습니다."))
  proj-name
)

;;;;==========================================================================
;;;; defun tsp-shape-mismatch-prompt : 경계선 형상/선분 수 불일치 시 [수동 데이터 매칭] 선택 팝업
;;;;==========================================================================
(defun tsp-shape-mismatch-prompt (msg1 msg2 msg3 / dcl-file fn dcl-id res)
  (setq dcl-file (strcat (getvar "TEMPPREFIX") "tsp_mismatch.dcl"))
  (setq fn (open dcl-file "w"))
  (if fn
    (progn
      (write-line "tsp_mismatch_dlg : dialog { label = \"AutoCAD 메시지 - 경계선 불일치\";" fn)
      (write-line "  : column {" fn)
      (write-line "    : spacer { height = 0.5; }" fn)
      (write-line "    : text { key = \"msg1\"; width = 62; alignment = centered; }" fn)
      (write-line "    : text { key = \"msg2\"; width = 62; alignment = centered; }" fn)
      (write-line "    : spacer { height = 0.3; }" fn)
      (write-line "    : text { key = \"msg3\"; width = 62; alignment = centered; }" fn)
      (write-line "    : spacer { height = 0.8; }" fn)
      (write-line "    : row { alignment = centered;" fn)
      (write-line "      : button { key = \"btn_match\"; label = \"수동 데이터 매칭\"; is_default = true; width = 20; }" fn)
      (write-line "      : button { key = \"cancel\"; label = \"취소\"; is_cancel = true; width = 14; }" fn)
      (write-line "    }" fn)
      (write-line "  }" fn)
      (write-line "}" fn)
      (close fn)
      (setq dcl-id (load_dialog dcl-file))
      (if (and dcl-id (>= dcl-id 0) (new_dialog "tsp_mismatch_dlg" dcl-id))
        (progn
          (set_tile "msg1" (if msg1 msg1 ""))
          (set_tile "msg2" (if msg2 msg2 ""))
          (set_tile "msg3" (if msg3 msg3 ""))
          (action_tile "btn_match" "(done_dialog 1)")
          (action_tile "cancel" "(done_dialog 0)")
          (setq res (start_dialog))
          (unload_dialog dcl-id)
          (vl-file-delete dcl-file)
          (= res 1)
        )
        (progn
          (if (and dcl-id (>= dcl-id 0)) (unload_dialog dcl-id))
          (vl-file-delete dcl-file)
          nil
        )
      )
    )
    nil
  )
)
