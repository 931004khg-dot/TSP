;;; ==========================================================================
;;; 파일명: TSP_5B_DCL_and_Strut.lsp
;;; 구  분: DCL 다이얼로그 UI, 세그먼트 매니저 및 버팀보/앵커/까치발 수동 작도 (Part B)
;;; 역  할: 전체 DCL 생성, 세그먼트 매니저/마법사/대시보드, 지반/범례/벽체/사보강재/지보재 콜백, 수동 버팀보/까치발/연속보강재/앵커편심각/중간말뚝 작도 및 제어 [create-tsp-dcl]
;;; 포함 함수: create-tsp-dcl
;;; --------------------------------------------------------------------------
;;; [안내] 이 파일은 TSP.lsp(메인 로더)에 의해 자동으로 로드되는 하위 모듈입니다.
;;;        코드 수정 시 전체 파일을 합칠 필요 없이 이 파일만 단독 패치하면 됩니다.
;;; ==========================================================================

;;;;==========================================================================
;;;; defun create-tsp-dcl : 임시 DCL 파일을 생성하여 각종 UI 다이얼로그의 형태를 정의하고, 해당 파일의 경로를 반환하는 함수
;;;;==========================================================================
(defun create-tsp-dcl (/ dcl-file dcl-path)
  (setq dcl-path (strcat (getvar "TEMPPREFIX") "tsp.dcl"))
  (setq dcl-file (open dcl-path "w"))
  (if dcl-file
    (progn
      ;; ----------------------------------------------------------------------
      ;; [DCL 0] tsp_main_menu : 초기 시작 메뉴
      ;; ----------------------------------------------------------------------
      (write-line "tsp_main_menu : dialog { label = \"TSP 메인 메뉴\"; " dcl-file)
      (write-line "  : column { alignment = centered; " dcl-file)
      (write-line "    : button { key = \"btn_run\"; label = \"프로젝트 실행 (도면작업)\"; width = 35; } " dcl-file)
      (write-line "    : spacer { height = 0.5; } " dcl-file)
      (write-line "    : button { key = \"btn_load_dwg\"; label = \"도면 내 프로젝트 불러오기\"; width = 35; } " dcl-file)
      (write-line "    : button { key = \"btn_export\"; label = \"EXCEL(CSV)로 내보내기\"; width = 35; } " dcl-file)
      (write-line "    : button { key = \"btn_import\"; label = \"EXCEL(CSV)에서 불러오기\"; width = 35; } " dcl-file)
      (write-line "    : spacer { height = 1.0; } " dcl-file)
      (write-line "    : button { key = \"cancel\"; label = \"종료\"; is_cancel = true; width = 35; } " dcl-file)
      (write-line "  } " dcl-file)
      (write-line "} " dcl-file)

      ;; ----------------------------------------------------------------------
      ;; [DCL 1] tsp_scale : 도면 스케일 설정
      ;; ----------------------------------------------------------------------
      (write-line "tsp_scale : dialog { label = \"스케일 설정\"; " dcl-file)
      (write-line "  : column { alignment = centered; " dcl-file)
      (write-line "    : row { alignment = centered; fixed_width = true; " dcl-file)
      (write-line "      : edit_box { key = \"scale_section\"; label = \"단면도 A3 : 1/\"; edit_width = 3; width = 10; fixed_width = true; } " dcl-file)
      (write-line "    } " dcl-file)
      (write-line "    : row { alignment = centered; fixed_width = true; " dcl-file)
      (write-line "      : edit_box { key = \"scale_plan\"; label = \"평면도 A3 : 1/\"; edit_width = 3; width = 10; fixed_width = true; } " dcl-file)
      (write-line "    } " dcl-file)
      (write-line "  } " dcl-file)
      (write-line "  : spacer { height = 1.0; } " dcl-file)
      (write-line "  : row { alignment = centered; " dcl-file)
      (write-line "    : button { key = \"accept\"; label = \"확인\"; is_default = true; width = 12; } " dcl-file)
      (write-line "    : button { key = \"back\"; label = \"이전\"; width = 12; } " dcl-file)
      (write-line "    : button { key = \"cancel\"; label = \"취소\"; is_cancel = true; width = 12; } " dcl-file)
      (write-line "  } " dcl-file)
      (write-line "} " dcl-file)

      ;; ----------------------------------------------------------------------
      ;; [DCL 2] tsp_load_list : 저장된 프로젝트 관리 및 불러오기
      ;; ----------------------------------------------------------------------
      (write-line "tsp_load_list : dialog { label = \"프로젝트 관리\"; " dcl-file)
      (write-line "  : list_box { key = \"proj_list\"; label = \"저장된 프로젝트:\"; width = 30; height = 10; } " dcl-file)
      (write-line "  : row { alignment = centered; " dcl-file)
      (write-line "    : button { key = \"accept\"; label = \"불러오기\"; is_default = true; } " dcl-file)
      (write-line "    : button { key = \"btn_del_proj\"; label = \"삭제\"; } " dcl-file)
      (write-line "    : button { key = \"cancel\"; label = \"취소\"; is_cancel = true; } " dcl-file)
      (write-line "  } " dcl-file)
      (write-line "} " dcl-file)

      ;; ----------------------------------------------------------------------
      ;; [DCL 3] tsp_save_prompt : 다른 이름으로 프로젝트 저장 확인
      ;; ----------------------------------------------------------------------
      (write-line "tsp_save_prompt : dialog { label = \"프로젝트 저장\"; " dcl-file)
      (write-line "  : text { label = \"다른 이름으로 저장하시겠습니까?\"; alignment = centered; } " dcl-file)
      (write-line "  : spacer { height = 0.5; } " dcl-file)
      (write-line "  : row { alignment = centered; " dcl-file)
      (write-line "    : button { key = \"btn_yes\"; label = \"예 (새로 저장)\"; is_default = true; width = 18; } " dcl-file)
      (write-line "    : button { key = \"btn_no\"; label = \"아니오 (덮어쓰기)\"; width = 18; } " dcl-file)
      (write-line "    : button { key = \"cancel\"; label = \"취소\"; is_cancel = true; width = 12; } " dcl-file)
      (write-line "  } " dcl-file)
      (write-line "} " dcl-file)

      ;; ----------------------------------------------------------------------
      ;; [DCL 3-1] tsp_export_csv_prompt : CSV 내보내기 전 프로젝트 이름 확인/수정 팝업
      ;; ----------------------------------------------------------------------
      (write-line "tsp_export_csv_prompt : dialog { label = \"프로젝트 저장 및 CSV 내보내기\"; " dcl-file)
      (write-line "  : column { " dcl-file)
      (write-line "    : text { label = \"저장 및 내보낼 프로젝트 이름을 확인하세요. (그대로 Enter 시 현재 이름으로 저장)\"; alignment = centered; } " dcl-file)
      (write-line "    : spacer { height = 0.4; } " dcl-file)
      (write-line "    : edit_box { key = \"exp_proj_name\"; label = \"프로젝트 이름:\"; edit_width = 28; allow_accept = true; } " dcl-file)
      (write-line "    : spacer { height = 0.5; } " dcl-file)
      (write-line "    : row { alignment = centered; " dcl-file)
      (write-line "      : button { key = \"accept\"; label = \"확인 (저장 및 내보내기)\"; is_default = true; width = 22; } " dcl-file)
      (write-line "      : button { key = \"cancel\"; label = \"취소\"; is_cancel = true; width = 12; } " dcl-file)
      (write-line "    } " dcl-file)
      (write-line "  } " dcl-file)
      (write-line "} " dcl-file)

     ;; ----------------------------------------------------------------------
      ;; [DCL 4] tsp_section_choice : 단면도 생성 유형 선택 (일반/모서리) 및 서브그룹 선택
      ;; ----------------------------------------------------------------------
      (write-line "tsp_section_choice : dialog { label = \"단면도 생성 선택\"; " dcl-file)
      (write-line "  : column { " dcl-file)
      (write-line "    : text { label = \"작성할 단면도를 선택하세요:\"; alignment = centered; } " dcl-file)
      (write-line "    : spacer { height = 0.5; } " dcl-file)
      (write-line "    : toggle { key = \"chk_seg_sec\"; label = \"세그먼트(일반) 단면도\"; value = \"0\"; } " dcl-file)
      (write-line "    : toggle { key = \"chk_cor_sec\"; label = \"모서리 사보강재(Corner Strut) 단면도\"; value = \"0\"; } " dcl-file)
      (write-line "    : spacer { height = 0.5; } " dcl-file)
      (write-line "    : row { alignment = centered; " dcl-file)
      (write-line "      : button { key = \"accept\"; label = \"확인\"; is_default = true; width = 12; } " dcl-file)
      (write-line "      : button { key = \"cancel\"; label = \"취소\"; is_cancel = true; width = 12; } " dcl-file)
      (write-line "    } " dcl-file)
      (write-line "  } " dcl-file)
      (write-line "} " dcl-file)

      (write-line "tsp_subgrp_choice : dialog { label = \"단면도 기준 버팀보(Sub-group) 선택\"; " dcl-file)
      (write-line "  : column { " dcl-file)
      (write-line "    : text { key = \"subgrp_msg\"; label = \"동일 굴착단계에 여러 Sub-group이 존재합니다.\"; alignment = centered; } " dcl-file)
      (write-line "    : text { label = \"단면도에 작도할 기준 Sub-group을 선택하세요:\"; alignment = centered; } " dcl-file)
      (write-line "    : spacer { height = 0.5; } " dcl-file)
      (write-line "    : list_box { key = \"subgrp_list\"; width = 55; height = 6; } " dcl-file)
      (write-line "    : spacer { height = 0.5; } " dcl-file)
      (write-line "    : row { alignment = centered; " dcl-file)
      (write-line "      : button { key = \"accept\"; label = \"확인\"; is_default = true; width = 12; } " dcl-file)
      (write-line "      : button { key = \"cancel\"; label = \"취소\"; is_cancel = true; width = 12; } " dcl-file)
      (write-line "    } " dcl-file)
      (write-line "  } " dcl-file)
      (write-line "} " dcl-file)

      ;; ----------------------------------------------------------------------
      ;; [DCL 5] tsp_manager : 세그먼트 메인 관리창
      ;; ----------------------------------------------------------------------
      (write-line "tsp_manager : dialog { key = \"manager_title\"; label = \"세그먼트 설정 (Segment Manager)\"; " dcl-file)
      (write-line "  : column { " dcl-file)
      (write-line "    : row { " dcl-file)
      (write-line "      : text { label = \"No.\"; width = 4; } " dcl-file)
      (write-line "      : text { label = \"이름\"; width = 10; } " dcl-file)
      (write-line "      : text { label = \"단면\"; width = 6; } " dcl-file)
      (write-line "      : text { label = \"흙막이벽\"; width = 12; } " dcl-file)
      (write-line "      : text { label = \"H-pile/띠장 규격\"; width = 28; } " dcl-file)
      (write-line "      : text { label = \"지보재\"; width = 15; } " dcl-file)
      (write-line "      : text { label = \"사보강재(Corner Strut)\"; width = 25; } " dcl-file)
      (write-line "    } " dcl-file)
      (write-line (strcat "    : list_box { key = \"seg_list\"; width = 115; height = 15; "
                          "fixed_width = true; fixed_height = true; allow_accept = true; "
                          "multiple_select = true; tabs = \"5 15 21 33 60 75\"; } ") dcl-file)
      (write-line "    : text { key = \"status_msg\"; value = \"목록을 선택하고 입력 버튼을 누르세요.\"; alignment = centered; } " dcl-file)
      (write-line "  } " dcl-file)
      (write-line "  : spacer { height = 0.2; } " dcl-file)
      (write-line "  : row { alignment = centered; " dcl-file)
      (write-line "    : edit_box { key = \"project_name\"; label = \"프로젝트 이름:\"; width = 25; } " dcl-file)
      (write-line "    : button { key = \"btn_load_proj\"; label = \"불러오기\"; width = 12; } " dcl-file)
      (write-line "    : button { key = \"btn_load_csv\"; label = \"CSV 불러오기\"; width = 14; } " dcl-file)
      (write-line "    : button { key = \"btn_export_csv\"; label = \"CSV 내보내기\"; width = 14; } " dcl-file)
      (write-line "    : button { key = \"btn_save_proj\"; label = \"저장\"; width = 12; } " dcl-file)
      (write-line "  } " dcl-file)
      (write-line "  : spacer { height = 0.2; } " dcl-file)
      (write-line "  : row { alignment = centered; " dcl-file)
      (write-line "    : button { key = \"btn_input\"; label = \"입력 (Input)\"; is_default = true; width = 18; } " dcl-file)
      (write-line "    : button { key = \"btn_modify\"; label = \"수정 (Edit)\"; width = 18; } " dcl-file)
      (write-line "    : button { key = \"btn_delete\"; label = \"초기화 (Reset)\"; width = 18; } " dcl-file)
      (write-line "    : button { key = \"btn_copy_from\"; label = \"설정 가져오기\"; width = 22; } " dcl-file)
      (write-line "  } " dcl-file)
      (write-line "  : row { alignment = centered; " dcl-file)
      (write-line "    : button { key = \"btn_apply_all\"; label = \"전체 설정 일괄 적용\"; width = 30; } " dcl-file)
      (write-line "    : button { key = \"btn_delete_all\"; label = \"전체 목록 초기화 (Reset All)\"; width = 30; } " dcl-file)
      (write-line "  } " dcl-file)
      (write-line "  : row { alignment = centered; " dcl-file)
      (write-line "    : button { key = \"btn_apply_soil\"; label = \"지반 정보 복사\"; width = 30; } " dcl-file)
      (write-line "    : button { key = \"btn_apply_support\"; label = \"지보재 정보 복사\"; width = 30; } " dcl-file)
      (write-line "  } " dcl-file)
      (write-line "  : row { alignment = centered; " dcl-file)
      (write-line "    : button { key = \"btn_apply_wall\"; label = \"흙막이벽 정보 복사\"; width = 30; } " dcl-file)
      (write-line "    : button { key = \"btn_apply_brace\"; label = \"사보강재 정보 복사\"; width = 30; } " dcl-file)
      (write-line "  } " dcl-file)
      (write-line "  : spacer { height = 0.5; } " dcl-file)
      (write-line "  : row { alignment = centered; " dcl-file)
      (write-line "    : button { key = \"btn_measure\"; label = \"도면에서 확인/측정 (Measure)\"; width = 30; } " dcl-file)
      (write-line "  } " dcl-file)
      (write-line "  : spacer { height = 1.0; } " dcl-file)
      (write-line "  : row { alignment = centered; " dcl-file)
      (write-line "    : button { key = \"btn_draw_section\"; label = \"단면도 생성 (Section)\"; width = 22; } " dcl-file)
      (write-line "    : button { key = \"btn_draw_plan\"; label = \"평면도 생성 (Plan)\"; width = 22; } " dcl-file)
      (write-line "    : button { key = \"btn_draw_elev\"; label = \"전개도 생성 (Elev)\"; width = 22; } " dcl-file)
      (write-line "    : button { key = \"cancel\"; label = \"종료 (Exit)\"; is_cancel = true; width = 18; } " dcl-file)
      (write-line "  } " dcl-file)
      (write-line "} " dcl-file)

      ;; ----------------------------------------------------------------------
      ;; [DCL 6] tsp_edit_menu : 개별 세그먼트 상세 설정 (지반/흙막이/지보재 등)
      ;; ----------------------------------------------------------------------
      (write-line "tsp_edit_menu : dialog { key = \"menu_title\"; label = \"세그먼트 설정 수정\"; " dcl-file)
      (write-line "  : column { " dcl-file)
      (write-line "    : row { " dcl-file)
      (write-line "      : edit_box { key = \"seg_name\"; label = \"이름 입력 :\"; width = 20; } " dcl-file)
      (write-line "      : toggle { key = \"chk_section\"; label = \"단면생성 (지반 정보 포함)\"; } " dcl-file)
      (write-line "    } " dcl-file)
      (write-line "    : spacer { height = 0.5; } " dcl-file)
      (write-line "    : button { key = \"btn_soil\"; label = \"지반 정의 (Soil)\"; width = 40; fixed_width = true; alignment = centered; } " dcl-file)
      (write-line "    : button { key = \"btn_wall\"; label = \"흙막이벽 정의 (Wall)\"; width = 40; fixed_width = true; alignment = centered; } " dcl-file)
      (write-line "    : button { key = \"btn_support\"; label = \"지보재 정의 (Support)\"; width = 40; fixed_width = true; alignment = centered; } " dcl-file)
      (write-line "    : button { key = \"btn_brace\"; label = \"사보강재(Corner Strut) 정의\"; width = 40; fixed_width = true; alignment = centered; } " dcl-file)
      (write-line "  } " dcl-file)
      (write-line "  : spacer { height = 1; } " dcl-file)
      (write-line "  : row { alignment = centered; " dcl-file)
      (write-line "    : button { key = \"accept\"; label = \"확인 (저장)\"; is_default = true; width = 15; } " dcl-file)
      (write-line "    : button { key = \"cancel\"; label = \"취소\"; is_cancel = true; width = 15; } " dcl-file)
      (write-line "  } " dcl-file)
      (write-line "} " dcl-file)

            ;; ----------------------------------------------------------------------
      ;; [DCL 7-0] tsp_brace_def & tsp_brace_def_single : 사보강재(Corner Strut) 단별 정의(목록) 관리창
      ;; ----------------------------------------------------------------------
      (write-line "tsp_brace_def : dialog { key = \"brace_def_title\"; label = \"사보강재(Corner Strut) 정의 (단별 목록 관리)\"; " dcl-file)
      (write-line "  : column { " dcl-file)
      (write-line "    : text { key = \"brace_def_info\"; label = \"사보강재를 설치깊이 순서대로 추가/복사/수정할 수 있습니다.\"; alignment = centered; } " dcl-file)
      (write-line "    : spacer { height = 0.3; } " dcl-file)
      (write-line "    : list_box { key = \"brace_stage_list\"; label = \"단별 사보강재 목록 (설치깊이 오름차순):\"; width = 78; height = 10; fixed_width = true; fixed_height = true; multiple_select = false; } " dcl-file)
      (write-line "    : spacer { height = 0.4; } " dcl-file)
      (write-line "    : row { alignment = centered; " dcl-file)
      (write-line "      : button { key = \"btn_stage_add\"; label = \"추가\"; width = 14; } " dcl-file)
      (write-line "      : button { key = \"btn_stage_mod\"; label = \"수정\"; width = 14; } " dcl-file)
      (write-line "      : button { key = \"btn_stage_copy\"; label = \"선택 복사 추가\"; width = 18; } " dcl-file)
      (write-line "      : button { key = \"btn_stage_del\"; label = \"삭제\"; width = 14; } " dcl-file)
      (write-line "      : button { key = \"btn_stage_clear\"; label = \"전체삭제\"; width = 14; } " dcl-file)
      (write-line "    } " dcl-file)
      (write-line "    : spacer { height = 0.4; } " dcl-file)
      (write-line "    : boxed_column { label = \"코너부 띠장 상향 (Splice)\"; " dcl-file)
      (write-line "      : row { " dcl-file)
      (write-line "        : toggle { key = \"chk_upgrade_wale\"; label = \"사보강재(Corner Strut) 구간 띠장 상향 적용\"; } " dcl-file)
      (write-line "        : popup_list { key = \"upgrade_wale_spec\"; width = 22; } " dcl-file)
      (write-line "      } " dcl-file)
      (write-line "      : row { alignment = right; " dcl-file)
      (write-line "        : button { key = \"btn_sel_upg_limit\"; label = \"상향 범위(H-pile) 수동 선택\"; width = 26; } " dcl-file)
      (write-line "        : button { key = \"btn_reset_upg_limit\"; label = \"선택 초기화\"; width = 14; } " dcl-file)
      (write-line "      } " dcl-file)
      (write-line "    } " dcl-file)
      (write-line "    : spacer { height = 0.4; } " dcl-file)
      (write-line "    : row { alignment = centered; : button { key = \"btn_measure\"; label = \"도면에서 확인/측정\"; width = 26; } } " dcl-file)
      (write-line "    : spacer { height = 0.4; } " dcl-file)
      (write-line "    : row { alignment = centered; " dcl-file)
      (write-line "      : button { key = \"accept\"; label = \"다음 모서리\"; is_default = true; width = 14; } " dcl-file)
      (write-line "      : button { key = \"btn_comp\"; label = \"완료\"; width = 14; } " dcl-file)
      (write-line "      : button { key = \"cancel\"; label = \"취소\"; is_cancel = true; width = 14; } " dcl-file)
      (write-line "    } " dcl-file)
      (write-line "  } " dcl-file)
      (write-line "} " dcl-file)

      (write-line "tsp_brace_def_single : dialog { key = \"brace_def_title\"; label = \"사보강재(Corner Strut) 정의 (단별 목록 관리)\"; " dcl-file)
      (write-line "  : column { " dcl-file)
      (write-line "    : text { key = \"brace_def_info\"; label = \"사보강재를 설치깊이 순서대로 추가/복사/수정할 수 있습니다.\"; alignment = centered; } " dcl-file)
      (write-line "    : spacer { height = 0.3; } " dcl-file)
      (write-line "    : list_box { key = \"brace_stage_list\"; label = \"단별 사보강재 목록 (설치깊이 오름차순):\"; width = 78; height = 10; fixed_width = true; fixed_height = true; multiple_select = false; } " dcl-file)
      (write-line "    : spacer { height = 0.4; } " dcl-file)
      (write-line "    : row { alignment = centered; " dcl-file)
      (write-line "      : button { key = \"btn_stage_add\"; label = \"추가\"; width = 14; } " dcl-file)
      (write-line "      : button { key = \"btn_stage_mod\"; label = \"수정\"; width = 14; } " dcl-file)
      (write-line "      : button { key = \"btn_stage_copy\"; label = \"선택 복사 추가\"; width = 18; } " dcl-file)
      (write-line "      : button { key = \"btn_stage_del\"; label = \"삭제\"; width = 14; } " dcl-file)
      (write-line "      : button { key = \"btn_stage_clear\"; label = \"전체삭제\"; width = 14; } " dcl-file)
      (write-line "    } " dcl-file)
      (write-line "    : spacer { height = 0.4; } " dcl-file)
      (write-line "    : boxed_column { label = \"코너부 띠장 상향 (Splice)\"; " dcl-file)
      (write-line "      : row { " dcl-file)
      (write-line "        : toggle { key = \"chk_upgrade_wale\"; label = \"사보강재(Corner Strut) 구간 띠장 상향 적용\"; } " dcl-file)
      (write-line "        : popup_list { key = \"upgrade_wale_spec\"; width = 22; } " dcl-file)
      (write-line "      } " dcl-file)
      (write-line "      : row { alignment = right; " dcl-file)
      (write-line "        : button { key = \"btn_sel_upg_limit\"; label = \"상향 범위(H-pile) 수동 선택\"; width = 26; } " dcl-file)
      (write-line "        : button { key = \"btn_reset_upg_limit\"; label = \"선택 초기화\"; width = 14; } " dcl-file)
      (write-line "      } " dcl-file)
      (write-line "    } " dcl-file)
      (write-line "    : spacer { height = 0.4; } " dcl-file)
      (write-line "    : row { alignment = centered; : button { key = \"btn_measure\"; label = \"도면에서 확인/측정\"; width = 26; } } " dcl-file)
      (write-line "    : spacer { height = 0.4; } " dcl-file)
      (write-line "    : row { alignment = centered; " dcl-file)
      (write-line "      : button { key = \"accept\"; label = \"다음 모서리\"; width = 14; } " dcl-file)
      (write-line "      : button { key = \"btn_comp\"; label = \"완료\"; is_default = true; width = 14; } " dcl-file)
      (write-line "      : button { key = \"cancel\"; label = \"취소\"; is_cancel = true; width = 14; } " dcl-file)
      (write-line "    } " dcl-file)
      (write-line "  } " dcl-file)
      (write-line "} " dcl-file)

      ;; ----------------------------------------------------------------------
      ;; [DCL 7] tsp_brace & tsp_brace_single : 사보강재(Corner Strut) 단별 세부 설정 다이얼로그
      ;; ----------------------------------------------------------------------
            (write-line "tsp_brace : dialog { key = \"brace_dlg_title\"; label = \"사보강재(Corner Strut) 세부 설정\"; " dcl-file)
      (write-line "  : column { " dcl-file)
      (write-line "    : text { key = \"brace_info\"; label = \"최대 한계 거리: -- m\"; alignment = centered; } " dcl-file)
      (write-line "    : row { " dcl-file)
      (write-line "      : edit_box { key = \"brace_stage_name\"; label = \"단 이름:\"; edit_width = 14; } " dcl-file)
      (write-line "      : edit_box { key = \"brace_stage_depth\"; label = \"설치깊이(m):\"; edit_width = 10; } " dcl-file)
      (write-line "    } " dcl-file)
      (write-line "    : list_box { key = \"brace_list\"; height = 6; width = 70; multiple_select = true; } " dcl-file)
      (write-line "    : row { " dcl-file)
      (write-line "      : text { label = \"이격 거리(m):\"; width = 12; } " dcl-file)
      (write-line "      : edit_box { key = \"brace_dist\"; width = 10; } " dcl-file)
      (write-line "    } " dcl-file)
      (write-line "    : text { label = \"※ 1열은 코너 기준, 2열부터는 이전 열 기준 상대거리입니다.\"; } " dcl-file)
      (write-line "    : spacer { height = 0.5; } " dcl-file)
      (write-line "    : text { label = \"사보강재(Corner Strut) 규격\"; } " dcl-file)
      (write-line "    : popup_list { key = \"brace_spec\"; width = 30; } " dcl-file)
      (write-line "    : row { " dcl-file)
      (write-line "      : edit_box { key = \"brace_h\"; width = 5; is_enabled = false; } " dcl-file)
      (write-line "      : text { label = \"x\"; } " dcl-file)
      (write-line "      : edit_box { key = \"brace_b\"; width = 5; is_enabled = false; } " dcl-file)
      (write-line "      : text { label = \"x\"; } " dcl-file)
      (write-line "      : edit_box { key = \"brace_tw\"; width = 5; is_enabled = false; } " dcl-file)
      (write-line "      : text { label = \"/\"; } " dcl-file)
      (write-line "      : edit_box { key = \"brace_tf\"; width = 5; is_enabled = false; } " dcl-file)
      (write-line "    } " dcl-file)
      (write-line "    : spacer { height = 0.5; } " dcl-file)
      (write-line "    : row { " dcl-file)
      (write-line "      : popup_list { key = \"brace_jack\"; label = \"잭 종류:\"; width = 20; } " dcl-file)
      (write-line "      : popup_list { key = \"brace_jack_side\"; label = \"잭 위치:\"; width = 28; } " dcl-file)
      (write-line "    } " dcl-file)
      (write-line "    : row { " dcl-file)
      (write-line "      : popup_list { key = \"brace_conn\"; label = \"연결 방식:\"; width = 28; } " dcl-file)
      (write-line "    } " dcl-file)
      (write-line "    : spacer { height = 0.5; } " dcl-file)
      (write-line "    : row { alignment = centered; " dcl-file)
      (write-line "      : button { key = \"btn_add\"; label = \"추가\"; } " dcl-file)
      (write-line "      : button { key = \"btn_mod\"; label = \"수정\"; } " dcl-file)
      (write-line "      : button { key = \"btn_del\"; label = \"삭제\"; } " dcl-file)
      (write-line "    } " dcl-file)
      (write-line "    : spacer { height = 0.5; } " dcl-file)
      (write-line "    : boxed_column { label = \"보강재(Brace) 설정\"; " dcl-file)
      (write-line "      : toggle { key = \"chk_stiffener_enable\"; label = \"보강재(Brace) 생성 적용\"; } " dcl-file)
      (write-line "      : row { : text { label = \"설계 세장비 한계:\"; width = 16; } : popup_list { key = \"slenderness_limit\"; width = 20; } } " dcl-file)
      (write-line "      : row { : toggle { key = \"chk_manual_interval\"; label = \"간격 입력(m):\"; width = 16; } : edit_box { key = \"stiffener_interval\"; width = 10; } } " dcl-file)
      (write-line "      : text { key = \"stiffener_info\"; label = \"계산된 필요 간격: -- m\"; alignment = centered; } " dcl-file)
      (write-line "      : row { : text { label = \"보강재 여유장(mm) :\"; width = 16; } : edit_box { key = \"stiffener_margin\"; width = 10; } } " dcl-file)
      (write-line "    } " dcl-file)
      (write-line "    : boxed_column { label = \"중간말뚝(Post pile) 설정\"; " dcl-file)
      (write-line "      : row { " dcl-file)
      (write-line "        : toggle { key = \"chk_post_enable\"; label = \"생성 적용\"; value = \"1\"; width = 12; } " dcl-file)
      (write-line "        : popup_list { key = \"post_layout_mode\"; label = \"배치:\"; width = 16; } " dcl-file)
      (write-line "        : toggle { key = \"chk_post_invert\"; label = \"교차 반전\"; } " dcl-file)
      (write-line "      } " dcl-file)
      (write-line "      : row { " dcl-file)
      (write-line "        : radio_row { key = \"post_side_grp\"; " dcl-file)
      (write-line "          : radio_button { key = \"post_side_L\"; label = \"보강재 왼쪽\"; value = \"1\"; } " dcl-file)
      (write-line "          : radio_button { key = \"post_side_R\"; label = \"보강재 오른쪽\"; } " dcl-file)
      (write-line "        } " dcl-file)
      (write-line "      } " dcl-file)
      (write-line "      : row { alignment = right; " dcl-file)
      (write-line "        : button { key = \"btn_post_add\"; label = \"추가\"; width = 10; } " dcl-file)
      (write-line "        : button { key = \"btn_post_del\"; label = \"삭제\"; width = 10; } " dcl-file)
      (write-line "        : button { key = \"btn_post_reset\"; label = \"초기화\"; width = 10; } " dcl-file)
      (write-line "      } " dcl-file)
      (write-line "    } " dcl-file)
      (write-line "    : boxed_column { label = \"코너부 띠장 상향 (Splice)\"; " dcl-file)
      (write-line "      : row { " dcl-file)
      (write-line "        : toggle { key = \"chk_upgrade_wale\"; label = \"사보강재(Corner Strut) 구간 띠장 상향 적용\"; is_enabled = false; } " dcl-file)
      (write-line "        : popup_list { key = \"upgrade_wale_spec\"; width = 20; is_enabled = false; } " dcl-file)
      (write-line "      } " dcl-file)
      (write-line "      : row { alignment = right; " dcl-file)
      (write-line "        : button { key = \"btn_sel_upg_limit\"; label = \"상향 범위(H-pile) 수동 선택\"; width = 25; } " dcl-file)
      (write-line "        : button { key = \"btn_reset_upg_limit\"; label = \"선택 초기화\"; width = 12; } " dcl-file)
      (write-line "      } " dcl-file)
      (write-line "    } " dcl-file)
      (write-line "    : spacer { height = 0.5; } " dcl-file)
      (write-line "    : row { alignment = centered; : button { key = \"btn_measure\"; label = \"도면에서 확인/측정\"; width = 25; } } " dcl-file)
      (write-line "    : spacer { height = 0.5; } " dcl-file)
      (write-line "    : row { alignment = centered; " dcl-file)
      (write-line "      : button { key = \"accept\"; label = \"다음\"; is_default = true; width = 12; } " dcl-file)
      (write-line "      : button { key = \"btn_comp\"; label = \"완료\"; width = 12; } " dcl-file)
      (write-line "      : button { key = \"cancel\"; label = \"취소\"; is_cancel = true; width = 12; } " dcl-file)
      (write-line "    } " dcl-file)
      (write-line "  } " dcl-file)
      (write-line "} " dcl-file)

                        (write-line "tsp_brace_single : dialog { key = \"brace_dlg_title\"; label = \"사보강재(Corner Strut) 세부 설정\"; " dcl-file)
      (write-line "  : column { " dcl-file)
      (write-line "    : text { key = \"brace_info\"; label = \"최대 한계 거리: -- m\"; alignment = centered; } " dcl-file)
      (write-line "    : row { " dcl-file)
      (write-line "      : edit_box { key = \"brace_stage_name\"; label = \"단 이름:\"; edit_width = 14; } " dcl-file)
      (write-line "      : edit_box { key = \"brace_stage_depth\"; label = \"설치깊이(m):\"; edit_width = 10; } " dcl-file)
      (write-line "    } " dcl-file)
      (write-line "    : list_box { key = \"brace_list\"; height = 6; width = 70; multiple_select = true; } " dcl-file)
      (write-line "    : row { " dcl-file)
      (write-line "      : text { label = \"이격 거리(m):\"; width = 12; } " dcl-file)
      (write-line "      : edit_box { key = \"brace_dist\"; width = 10; } " dcl-file)
      (write-line "    } " dcl-file)
      (write-line "    : text { label = \"※ 1열은 코너 기준, 2열부터는 이전 열 기준 상대거리입니다.\"; } " dcl-file)
      (write-line "    : spacer { height = 0.5; } " dcl-file)
      (write-line "    : text { label = \"사보강재(Corner Strut) 규격\"; } " dcl-file)
      (write-line "    : popup_list { key = \"brace_spec\"; width = 30; } " dcl-file)
      (write-line "    : row { " dcl-file)
      (write-line "      : edit_box { key = \"brace_h\"; width = 5; is_enabled = false; } " dcl-file)
      (write-line "      : text { label = \"x\"; } " dcl-file)
      (write-line "      : edit_box { key = \"brace_b\"; width = 5; is_enabled = false; } " dcl-file)
      (write-line "      : text { label = \"x\"; } " dcl-file)
      (write-line "      : edit_box { key = \"brace_tw\"; width = 5; is_enabled = false; } " dcl-file)
      (write-line "      : text { label = \"/\"; } " dcl-file)
      (write-line "      : edit_box { key = \"brace_tf\"; width = 5; is_enabled = false; } " dcl-file)
      (write-line "    } " dcl-file)
      (write-line "    : spacer { height = 0.5; } " dcl-file)
      (write-line "    : row { " dcl-file)
      (write-line "      : popup_list { key = \"brace_jack\"; label = \"잭 종류:\"; width = 20; } " dcl-file)
      (write-line "      : popup_list { key = \"brace_jack_side\"; label = \"잭 위치:\"; width = 28; } " dcl-file)
      (write-line "    } " dcl-file)
      (write-line "    : row { " dcl-file)
      (write-line "      : popup_list { key = \"brace_conn\"; label = \"연결 방식:\"; width = 28; } " dcl-file)
      (write-line "    } " dcl-file)
      (write-line "    : spacer { height = 0.5; } " dcl-file)
      (write-line "    : row { alignment = centered; " dcl-file)
      (write-line "      : button { key = \"btn_add\"; label = \"추가\"; } " dcl-file)
      (write-line "      : button { key = \"btn_mod\"; label = \"수정\"; } " dcl-file)
      (write-line "      : button { key = \"btn_del\"; label = \"삭제\"; } " dcl-file)
      (write-line "    } " dcl-file)
      (write-line "    : spacer { height = 0.5; } " dcl-file)
      (write-line "    : boxed_column { label = \"보강재(Brace) 설정\"; " dcl-file)
      (write-line "      : toggle { key = \"chk_stiffener_enable\"; label = \"보강재(Brace) 생성 적용\"; } " dcl-file)
      (write-line "      : row { : text { label = \"설계 세장비 한계:\"; width = 16; } : popup_list { key = \"slenderness_limit\"; width = 20; } } " dcl-file)
      (write-line "      : row { : toggle { key = \"chk_manual_interval\"; label = \"보강재 간격 입력(m):\"; width = 16; } : edit_box { key = \"stiffener_interval\"; width = 10; } } " dcl-file)
      (write-line "      : text { key = \"stiffener_info\"; label = \"계산된 필요 간격: -- m\"; alignment = centered; } " dcl-file)
      (write-line "      : row { : text { label = \"보강재 여유장(mm) :\"; width = 16; } : edit_box { key = \"stiffener_margin\"; width = 10; } } " dcl-file)
      (write-line "    } " dcl-file)
      (write-line "    : boxed_column { label = \"중간말뚝(Post pile) 설정\"; " dcl-file)
      (write-line "      : row { " dcl-file)
      (write-line "        : toggle { key = \"chk_post_enable\"; label = \"생성 적용\"; value = \"1\"; width = 12; } " dcl-file)
      (write-line "        : popup_list { key = \"post_layout_mode\"; label = \"배치:\"; width = 16; } " dcl-file)
      (write-line "        : toggle { key = \"chk_post_invert\"; label = \"교차 반전\"; } " dcl-file)
      (write-line "      } " dcl-file)
      (write-line "      : row { " dcl-file)
      (write-line "        : radio_row { key = \"post_side_grp\"; " dcl-file)
      (write-line "          : radio_button { key = \"post_side_L\"; label = \"보강재 왼쪽\"; value = \"1\"; } " dcl-file)
      (write-line "          : radio_button { key = \"post_side_R\"; label = \"보강재 오른쪽\"; } " dcl-file)
      (write-line "        } " dcl-file)
      (write-line "      } " dcl-file)
      (write-line "      : row { alignment = right; " dcl-file)
      (write-line "        : button { key = \"btn_post_add\"; label = \"추가\"; width = 10; } " dcl-file)
      (write-line "        : button { key = \"btn_post_del\"; label = \"삭제\"; width = 10; } " dcl-file)
      (write-line "        : button { key = \"btn_post_reset\"; label = \"초기화\"; width = 10; } " dcl-file)
      (write-line "      } " dcl-file)
      (write-line "    } " dcl-file)
      (write-line "    : boxed_column { label = \"코너부 띠장 상향 (Splice)\"; " dcl-file)
      (write-line "      : row { " dcl-file)
      (write-line "        : toggle { key = \"chk_upgrade_wale\"; label = \"사보강재(Corner Strut) 구간 띠장 상향 적용\"; is_enabled = false; } " dcl-file)
      (write-line "        : popup_list { key = \"upgrade_wale_spec\"; width = 20; is_enabled = false; } " dcl-file)
      (write-line "      } " dcl-file)
      (write-line "      : row { alignment = right; " dcl-file)
      (write-line "        : button { key = \"btn_sel_upg_limit\"; label = \"상향 범위(H-pile) 수동 선택\"; width = 30; } " dcl-file)
      (write-line "        : button { key = \"btn_reset_upg_limit\"; label = \"선택 초기화\"; width = 12; } " dcl-file)
      (write-line "      } " dcl-file)
      (write-line "    } " dcl-file)
      (write-line "    : spacer { height = 0.5; } " dcl-file)
      (write-line "    : row { alignment = centered; : button { key = \"btn_measure\"; label = \"도면에서 확인/측정\"; width = 25; } } " dcl-file)
      (write-line "    : spacer { height = 0.5; } " dcl-file)
      (write-line "    : row { alignment = centered; " dcl-file)
      (write-line "      : button { key = \"accept\"; label = \"다음\"; width = 12; } " dcl-file)
      (write-line "      : button { key = \"btn_comp\"; label = \"완료\"; is_default = true; width = 12; } " dcl-file)
      (write-line "      : button { key = \"cancel\"; label = \"취소\"; is_cancel = true; width = 12; } " dcl-file)
      (write-line "    } " dcl-file)
      (write-line "  } " dcl-file)
      (write-line "} " dcl-file)

      ;; ----------------------------------------------------------------------
      ;; [DCL 8] tsp_brace_warn & tsp_brace_hard_warn : 사보강재 한계 초과 경고
      ;; ----------------------------------------------------------------------
      (write-line "tsp_brace_angle_warn : dialog { label = \"경고: 완만한 코너 각도\"; " dcl-file)
      (write-line "  : text { key = \"angle_msg\"; label = \"코너 각도가 120도 이상입니다.\"; alignment = centered; } " dcl-file)
      (write-line "  : text { label = \"사보강재(Corner Strut) 설치 시 부재 간 간섭이 발생할 수 있습니다.\"; alignment = centered; } " dcl-file)
      (write-line "  : spacer { height = 0.5; } " dcl-file)
      (write-line "  : row { alignment = centered; " dcl-file)
      (write-line "    : button { key = \"btn_skip\"; label = \"생략 (Skip)\"; is_default = true; is_cancel = true; width = 12; } " dcl-file)
      (write-line "    : button { key = \"btn_cont\"; label = \"계속 (Continue)\"; width = 12; } " dcl-file)
      (write-line "  } " dcl-file)
      (write-line "} " dcl-file)

      (write-line "tsp_brace_warn : dialog { label = \"경고: 권장 공간 초과\"; " dcl-file)
      (write-line "  : text { label = \"입력한 누적거리가 권장 한계(50%)를 초과했습니다.\"; alignment = centered; } " dcl-file)
      (write-line "  : text { label = \"이웃 모서리의 사보강재(Corner Strut) 설치 공간이 부족해질 수 있습니다.\"; alignment = centered; } " dcl-file)
      (write-line "  : text { label = \"그래도 리스트에 추가(수정)하시겠습니까?\"; alignment = centered; } " dcl-file)
      (write-line "  : spacer { height = 0.5; } " dcl-file)
      (write-line "  : row { alignment = centered; " dcl-file)
      (write-line "    : button { key = \"accept\"; label = \"확인(계속)\"; is_default = true; width = 12; } " dcl-file)
      (write-line "    : button { key = \"cancel\"; label = \"취소\"; is_cancel = true; width = 12; } " dcl-file)
      (write-line "  } " dcl-file)
      (write-line "} " dcl-file)

      (write-line "tsp_brace_hard_warn : dialog { label = \"경고: 절대 한계 초과\"; " dcl-file)
      (write-line "  : text { key = \"warn_msg1\"; label = \"입력한 거리가 물리적 절대 한계를 초과했습니다!\"; alignment = centered; } " dcl-file)
      (write-line "  : text { key = \"warn_msg2\"; label = \"부재 간 간섭이 발생할 수 있습니다. 강제로 적용하시겠습니까?\"; alignment = centered; } " dcl-file)
      (write-line "  : spacer { height = 0.5; } " dcl-file)
      (write-line "  : row { alignment = centered; " dcl-file)
      (write-line "    : button { key = \"accept\"; label = \"강제 적용\"; is_default = true; width = 12; } " dcl-file)
      (write-line "    : button { key = \"cancel\"; label = \"취소\"; is_cancel = true; width = 12; } " dcl-file)
      (write-line "  } " dcl-file)
      (write-line "} " dcl-file)

      ;; ----------------------------------------------------------------------
      ;; [DCL 9] tsp_section_mode : 세그먼트 설정
      ;; ----------------------------------------------------------------------
      (write-line "tsp_section_mode : dialog { key = \"dlg_title\"; label = \"세그먼트 설정\"; " dcl-file)
      (write-line "  : column { " dcl-file)
      (write-line "    : row { " dcl-file)
      (write-line "      : text { label = \"이름 입력 :\"; } " dcl-file)
      (write-line "      : edit_box { key = \"seg_name\"; width = 20; } " dcl-file)
      (write-line "    } " dcl-file)
      (write-line "    : spacer { height = 0.5; } " dcl-file)
      (write-line "    : row { " dcl-file)
      (write-line "      : toggle { key = \"chk_section\"; label = \"단면생성 (지반 정보 포함)\"; } " dcl-file)
      (write-line "    } " dcl-file)
      (write-line "  } " dcl-file)
      (write-line "  : spacer { height = 1; } " dcl-file)
      (write-line "  : row { alignment = centered; " dcl-file)
      (write-line "    : button { key = \"accept\"; label = \"다음\"; is_default = true; width = 12; } " dcl-file)
      (write-line "    : button { key = \"cancel\"; label = \"취소\"; is_cancel = true; width = 12; } " dcl-file)
      (write-line "  } " dcl-file)
      (write-line "} " dcl-file)

      ;; ----------------------------------------------------------------------
      ;; [DCL 10] tsp_soil : 지반 정의
      ;; ----------------------------------------------------------------------
      (write-line "tsp_soil : dialog { label = \"지반 정의\"; " dcl-file)
      (write-line "  : column { " dcl-file)
      (write-line "    : text { label = \"지층 및 N치 정보를 입력하세요\"; alignment = centered; } " dcl-file)
      (write-line "    : spacer { height = 0.5; } " dcl-file)
      (write-line "    : row { " dcl-file)
      (write-line "      : edit_box { key = \"hole_no\"; label = \"HOLE No.\"; edit_width = 10; fixed_width = true; } " dcl-file)
      (write-line "      : spacer { } " dcl-file)
      (write-line "      : row { alignment = right; fixed_width = true; " dcl-file)
      (write-line "        : edit_box { key = \"soil_max_depth\"; label = \"최대굴착깊이(m)\"; edit_width = 6; fixed_width = true; } " dcl-file)
      (write-line "        : spacer { width = 1.0; fixed_width = true; } " dcl-file)
      (write-line "        : edit_box { key = \"soil_embed_depth\"; label = \"근입깊이(m)\"; edit_width = 6; fixed_width = true; } " dcl-file)
      (write-line "      } " dcl-file)
      (write-line "    } " dcl-file)
      (write-line "    : spacer { height = 0.5; } " dcl-file)
      (write-line "    : row { " dcl-file)
      (write-line (strcat "      : list_box { key = \"soil_list\"; label = \"지층 목록:\"; width = 72; "
                          "height = 12; fixed_width = true; fixed_height = true; multiple_select = false; } ") dcl-file)
      (write-line "      : spacer { width = 4.0; fixed_width = true; } " dcl-file)
      (write-line (strcat "      : list_box { key = \"n_val_list\"; label = \"N치 목록:\"; width = 45; "
                          "height = 12; fixed_width = true; fixed_height = true; multiple_select = false; } ") dcl-file)
      (write-line "    } " dcl-file)
      (write-line "    : spacer { height = 0.5; fixed_height = true; } " dcl-file)
      (write-line "    : row { " dcl-file)
      (write-line "      : column { width = 72; fixed_width = true; " dcl-file)
      (write-line "        : row { " dcl-file)
      (write-line "          : edit_box { key = \"soil_user_name\"; label = \"이름:\"; edit_width = 5; } " dcl-file)
      (write-line "          : popup_list { key = \"soil_type\"; label = \"종류:\"; edit_width = 15; } " dcl-file)
      (write-line "          : edit_box { key = \"soil_depth\"; label = \"깊이(m):\"; edit_width = 5; } " dcl-file)
      (write-line "          : edit_box { key = \"soil_phi\"; label = \"마찰각:\"; edit_width = 4; } " dcl-file)
      (write-line "        } " dcl-file)
      (write-line "      } " dcl-file)
      (write-line "      : spacer { width = 4.0; fixed_width = true; } " dcl-file)
      (write-line "      : column { width = 45; fixed_width = true; " dcl-file)
      (write-line "        : row { alignment = centered; " dcl-file)
      (write-line "          : text { label = \"N치(회/cm): \"; } " dcl-file)
      (write-line "          : edit_box { key = \"n_hit\"; edit_width = 4; fixed_width = true; } " dcl-file)
      (write-line "          : text { label = \"/\"; } " dcl-file)
      (write-line "          : edit_box { key = \"n_pen\"; edit_width = 4; fixed_width = true; } " dcl-file)
      (write-line "          : text { label = \"깊이:\"; } " dcl-file)
      (write-line "          : edit_box { key = \"n_depth\"; edit_width = 5; fixed_width = true; } " dcl-file)
      (write-line "        } " dcl-file)
      (write-line "      } " dcl-file)
      (write-line "    } " dcl-file)
      (write-line "    : spacer { height = 0.3; fixed_height = true; } " dcl-file)
      (write-line "    : row { " dcl-file)
      (write-line "      : column { width = 72; fixed_width = true; " dcl-file)
      (write-line "        : row { alignment = centered; " dcl-file)
      (write-line "          : button { key = \"btn_add\"; label = \"추가\"; width = 12; fixed_width = true; } " dcl-file)
      (write-line "          : button { key = \"btn_modify\"; label = \"수정\"; width = 12; fixed_width = true; } " dcl-file)
      (write-line "          : button { key = \"btn_delete\"; label = \"삭제\"; width = 12; fixed_width = true; } " dcl-file)
      (write-line "          : button { key = \"btn_clear\"; label = \"전체삭제\"; width = 12; fixed_width = true; } " dcl-file)
      (write-line "        } " dcl-file)
      (write-line "      } " dcl-file)
      (write-line "      : spacer { width = 4.0; fixed_width = true; } " dcl-file)
      (write-line "      : column { width = 45; fixed_width = true; " dcl-file)
      (write-line "        : row { alignment = centered; " dcl-file)
      (write-line "          : button { key = \"btn_n_add\"; label = \"추가\"; width = 10; fixed_width = true; } " dcl-file)
      (write-line "          : button { key = \"btn_n_modify\"; label = \"수정\"; width = 10; fixed_width = true; } " dcl-file)
      (write-line "          : button { key = \"btn_n_delete\"; label = \"삭제\"; width = 10; fixed_width = true; } " dcl-file)
      (write-line "          : button { key = \"btn_n_clear\"; label = \"전체삭제\"; width = 10; fixed_width = true; } " dcl-file)
      (write-line "        } " dcl-file)
      (write-line "        : spacer { height = 0.2; fixed_height = true; } " dcl-file)
      (write-line "        : row { alignment = centered; " dcl-file)
      (write-line "          : button { key = \"btn_n_get_dwg\"; label = \"도면에서 드래그하여 입력\"; width = 44; fixed_width = true; } " dcl-file)
      (write-line "        } " dcl-file)
      (write-line "        : spacer { height = 0.5; fixed_height = true; } " dcl-file)
      (write-line "        : row { alignment = centered; " dcl-file)
      (write-line "          : toggle { key = \"soil_water_chk\"; label = \"지하수위\"; } " dcl-file)
      (write-line "          : edit_box { key = \"soil_water_depth\"; label = \"GL -\"; edit_width = 8; is_enabled = false; } " dcl-file)
      (write-line "        } " dcl-file)
      (write-line "      } " dcl-file)
      (write-line "    } " dcl-file)
      (write-line "    : spacer { height = 1.0; fixed_height = true; } " dcl-file)
      (write-line "    : row { " dcl-file)
      (write-line "      : column { width = 72; fixed_width = true; " dcl-file)
      (write-line "        : boxed_column { label = \"숏크리트 설정\"; " dcl-file)
      (write-line "          : row { " dcl-file)
      (write-line "            : toggle { key = \"soil_shotcrete_enable\"; label = \"숏크리트 생성\"; } " dcl-file)
      (write-line "            : spacer { width = 1.0; fixed_width = true; } " dcl-file)
      (write-line "            : edit_box { key = \"soil_shotcrete_thick\"; label = \"두께(mm)\"; edit_width = 6; } " dcl-file)
      (write-line "          } " dcl-file)
      (write-line "          : row { " dcl-file)
      (write-line "            : toggle { key = \"soil_shotcrete_chk\"; label = \"숏크리트 암반층 선택\"; } " dcl-file)
      (write-line "            : popup_list { key = \"soil_shotcrete_layer\"; edit_width = 14; is_enabled = false; } " dcl-file)
      (write-line "          } " dcl-file)
      (write-line "        } " dcl-file)
      (write-line "      } " dcl-file)
      (write-line "      : spacer { width = 4.0; fixed_width = true; } " dcl-file)
      (write-line "      : column { width = 45; fixed_width = true; " dcl-file)
      (write-line "        : boxed_column { label = \"CIP 암반 정착 설정\"; " dcl-file)
      (write-line "          : row { " dcl-file)
      (write-line "            : toggle { key = \"soil_rock_embed_chk\"; label = \"CIP 암반 정착\"; } " dcl-file)
      (write-line "            : edit_box { key = \"soil_rock_embed\"; label = \"정착고(mm)\"; edit_width = 8; } " dcl-file)
      (write-line "          } " dcl-file)
      (write-line "          : row { " dcl-file)
      (write-line "            : toggle { key = \"soil_cip_rock_chk\"; label = \"CIP정착 암반층 선택\"; } " dcl-file)
      (write-line "            : popup_list { key = \"soil_cip_rock_layer\"; edit_width = 12; is_enabled = false; } " dcl-file)
      (write-line "          } " dcl-file)
      (write-line "        } " dcl-file)
      (write-line "      } " dcl-file)
      (write-line "    } " dcl-file)
      (write-line "    : spacer { height = 1.0; } " dcl-file)
      (write-line "    : row { alignment = centered; " dcl-file)
      (write-line "      : button { key = \"btn_legend\"; label = \"범례출력\"; width = 12; fixed_width = true; } " dcl-file)
      (write-line "      : button { key = \"btn_measure\"; label = \"도면에서 확인/측정\"; width = 18; fixed_width = true; } " dcl-file)
      (write-line "      : button { key = \"accept\"; label = \"확인\"; is_default = true; width = 12; } " dcl-file)
      (write-line "      : button { key = \"back\"; label = \"이전\"; width = 12; } " dcl-file)
      (write-line "      : button { key = \"cancel\"; label = \"취소\"; is_cancel = true; width = 12; } " dcl-file)
      (write-line "    } " dcl-file)
      (write-line "  } " dcl-file)
      (write-line "} " dcl-file)

      ;; ----------------------------------------------------------------------
      ;; [DCL 11] tsp_main : 흙막이벽 메인 메뉴
      ;; ----------------------------------------------------------------------
      (write-line "tsp_main : dialog { label = \"TSP - Temporary Structure Plan\"; " dcl-file)
      (write-line "  : column { alignment = centered; " dcl-file)
      (write-line "    : text { label = \"흙막이벽 정의\"; alignment = centered; } " dcl-file)
      (write-line "    : spacer { height = 0.5; } " dcl-file)
      (write-line "    : button { key = \"btn_hpile\"; label = \"H-Pile + 토류판\"; width = 30; fixed_width = true; } " dcl-file)
      (write-line "    : button { key = \"btn_cip\"; label = \"C.I.P (현장타설말뚝)\"; width = 30; fixed_width = true; } " dcl-file)
      (write-line "    : button { key = \"btn_scw\"; label = \"S.C.W (소일시멘트벽)\"; width = 30; fixed_width = true; is_enabled = false; } " dcl-file)
      (write-line "    : spacer { height = 0.5; } " dcl-file)
      (write-line "    : button { key = \"back\"; label = \"이전\"; width = 12; fixed_width = true; alignment = centered; } " dcl-file)
      (write-line "    : button { key = \"cancel\"; label = \"취소\"; is_cancel = true; fixed_width = true; alignment = centered; } " dcl-file)
      (write-line "  } " dcl-file)
      (write-line "} " dcl-file)

      ;; ----------------------------------------------------------------------
      ;; [DCL 12] tsp_hpile : H-Pile + 토류판 설정
      ;; ----------------------------------------------------------------------
      (write-line "tsp_hpile : dialog { label = \"H-Pile+토류판 설정\"; " dcl-file)
      (write-line "  : column { " dcl-file)
      (write-line "    : text { label = \"H-Pile 규격\"; } " dcl-file)
      (write-line "    : popup_list { key = \"hpile_spec\"; width = 30; fixed_width = true; } " dcl-file)
      (write-line "    : row { " dcl-file)
      (write-line "      : edit_box { key = \"hpile_h\"; width = 5; is_enabled = false; } " dcl-file)
      (write-line "      : text { label = \"x\"; } " dcl-file)
      (write-line "      : edit_box { key = \"hpile_b\"; width = 5; is_enabled = false; } " dcl-file)
      (write-line "      : text { label = \"x\"; } " dcl-file)
      (write-line "      : edit_box { key = \"hpile_tw\"; width = 5; is_enabled = false; } " dcl-file)
      (write-line "      : text { label = \"/\"; } " dcl-file)
      (write-line "      : edit_box { key = \"hpile_tf\"; width = 5; is_enabled = false; } " dcl-file)
      (write-line "    } " dcl-file)
      (write-line "    : spacer { height = 0.5; } " dcl-file)
      (write-line "    : row { " dcl-file)
      (write-line "      : text { label = \"C.T.C (m)\"; width = 10; } " dcl-file)
      (write-line "      : edit_box { key = \"ctc\"; width = 5; value = \"2\"; } " dcl-file)
      (write-line "    } " dcl-file)
      (write-line "    : spacer { height = 0.5; } " dcl-file)
      (write-line "    : text { label = \"띠장 규격\"; } " dcl-file)
      (write-line "    : popup_list { key = \"wale_spec\"; width = 30; fixed_width = true; } " dcl-file)
      (write-line "    : row { " dcl-file)
      (write-line "      : edit_box { key = \"wale_h\"; width = 5; is_enabled = false; } " dcl-file)
      (write-line "      : text { label = \"x\"; } " dcl-file)
      (write-line "      : edit_box { key = \"wale_b\"; width = 5; is_enabled = false; } " dcl-file)
      (write-line "      : text { label = \"x\"; } " dcl-file)
      (write-line "      : edit_box { key = \"wale_tw\"; width = 5; is_enabled = false; } " dcl-file)
      (write-line "      : text { label = \"/\"; } " dcl-file)
      (write-line "      : edit_box { key = \"wale_tf\"; width = 5; is_enabled = false; } " dcl-file)
      (write-line "    } " dcl-file)
      (write-line "    : spacer { height = 0.5; } " dcl-file)
      (write-line "    : row { " dcl-file)
      (write-line "      : text { label = \"토류판 두께 (mm)\"; width = 10; } " dcl-file)
      (write-line "      : edit_box { key = \"timber_thickness\"; width = 5; value = \"60\"; } " dcl-file)
      (write-line "    } " dcl-file)
      (write-line "    : spacer { height = 0.5; } " dcl-file)
      (write-line "    : row { " dcl-file)
      (write-line "      : text { label = \"그라우팅 선택\"; width = 10; } " dcl-file)
      (write-line "      : popup_list { key = \"hpile_grouting\"; width = 15; } " dcl-file)
      (write-line "    } " dcl-file)
      (write-line "    : spacer { height = 0.5; } " dcl-file)
      (write-line "    : row { " dcl-file)
      (write-line "      : text { label = \"그라우팅 간격\"; width = 10; } " dcl-file)
      (write-line "      : popup_list { key = \"hpile_grouting_space\"; width = 15; } " dcl-file)
      (write-line "      : edit_box { key = \"hpile_grouting_space_custom\"; width = 7; is_enabled = false; } " dcl-file)
      (write-line "    } " dcl-file)
      (write-line "    : spacer { height = 0.5; } " dcl-file)
      (write-line "    : row { " dcl-file)
      (write-line "      : text { label = \"그라우팅 기준선\"; width = 10; } " dcl-file)
      (write-line "      : popup_list { key = \"hpile_grouting_offset\"; width = 15; } " dcl-file)
      (write-line "      : edit_box { key = \"hpile_grouting_offset_custom\"; width = 7; is_enabled = false; } " dcl-file)
      (write-line "    } " dcl-file)
      (write-line "  } " dcl-file)
      (write-line "  : spacer { height = 1.0; } " dcl-file)
      (write-line "  : row { alignment = centered; " dcl-file)
      (write-line "    : button { key = \"accept\"; label = \"확인\"; is_default = true; width = 12; } " dcl-file)
      (write-line "    : button { key = \"back\"; label = \"이전\"; width = 12; } " dcl-file)
      (write-line "    : button { key = \"cancel\"; label = \"취소\"; is_cancel = true; width = 12; } " dcl-file)
      (write-line "  } " dcl-file)
      (write-line "} " dcl-file)

      ;; ----------------------------------------------------------------------
      ;; [DCL 13] tsp_support : 지보재 정의 (다중 선택 및 지보재 적용 구간 지정 지원)
      ;; ----------------------------------------------------------------------
      (write-line "tsp_support : dialog { label = \"지보재 정의\"; " dcl-file)
      (write-line "  : column { " dcl-file)
      (write-line "    : text { label = \"지보재 목록 관리 (Ctrl / Shift 클릭으로 다중 선택 후 적용 구간 일괄 지정 가능)\"; alignment = centered; } " dcl-file)
      (write-line "    : spacer { height = 0.5; } " dcl-file)
      (write-line (strcat "    : list_box { key = \"support_list\"; label = \"목록:\"; width = 82; "
                          "height = 12; fixed_width = true; fixed_height = true; multiple_select = true; } ") dcl-file)
      (write-line "    : spacer { height = 0.5; } " dcl-file)
      (write-line "    : row { " dcl-file)
      (write-line "      : popup_list { key = \"support_type_sel\"; label = \"추가할 유형:\"; width = 22; fixed_width = true; } " dcl-file)
      (write-line "      : button { key = \"btn_add\"; label = \"추가\"; width = 12; fixed_width = true; } " dcl-file)
      (write-line "      : button { key = \"btn_modify\"; label = \"수정\"; width = 12; fixed_width = true; } " dcl-file)
      (write-line "      : button { key = \"btn_delete\"; label = \"삭제\"; width = 12; fixed_width = true; } " dcl-file)
      (write-line "      : button { key = \"btn_clear\"; label = \"전체삭제\"; width = 12; fixed_width = true; } " dcl-file)
      (write-line "    } " dcl-file)
      (write-line "    : spacer { height = 0.3; } " dcl-file)
      (write-line "    : row { alignment = centered; " dcl-file)
      (write-line "      : button { key = \"btn_set_sup_range\"; label = \"지보재 적용 구간 지정 (H-Pile 클릭)\"; width = 38; fixed_width = true; } " dcl-file)
      (write-line "      : button { key = \"btn_reset_sup_range\"; label = \"선택 지보재 구간 초기화 (전체 적용)\"; width = 34; fixed_width = true; } " dcl-file)
      (write-line "    } " dcl-file)
      (write-line "  } " dcl-file)
      (write-line "  : spacer { height = 0.8; } " dcl-file)
      (write-line "  : row { alignment = centered; " dcl-file)
      (write-line "    : button { key = \"accept\"; label = \"확인\"; is_default = true; width = 12; fixed_width = true; } " dcl-file)
      (write-line "    : button { key = \"back\"; label = \"이전\"; width = 12; fixed_width = true; } " dcl-file)
      (write-line "    : button { key = \"cancel\"; label = \"취소\"; is_cancel = true; width = 12; fixed_width = true; } " dcl-file)
      (write-line "  } " dcl-file)
      (write-line "} " dcl-file)

      ;; ----------------------------------------------------------------------
      ;; [DCL 14] tsp_support_strut : 버팀보(Strut) 입력
      ;; ----------------------------------------------------------------------
      (write-line "tsp_support_strut : dialog { label = \"버팀보(Strut) 입력\"; " dcl-file)
      (write-line "  : column { " dcl-file)
      (write-line "    : row { " dcl-file)
      (write-line "      : edit_box { key = \"s_name\"; label = \"이름:\"; width = 15; } " dcl-file)
      (write-line "      : popup_list { key = \"s_shape\"; label = \"형상:\"; width = 15; } " dcl-file)
      (write-line "    } " dcl-file)
      (write-line "    : row { " dcl-file)
      (write-line "      : edit_box { key = \"s_depth\"; label = \"설치깊이(m):\"; width = 10; } " dcl-file)
      (write-line "      : popup_list { key = \"s_wale_spec\"; label = \"띠장 규격:\"; width = 22; } " dcl-file)
      (write-line "    } " dcl-file)
      (write-line "    : row { " dcl-file)
      (write-line "      : popup_list { key = \"s_mat\"; label = \"재질:\"; width = 15; } " dcl-file)
      (write-line "      : popup_list { key = \"s_sec\"; label = \"단면:\"; width = 20; } " dcl-file)
      (write-line "    } " dcl-file)
      (write-line "    : row { " dcl-file)
      (write-line "      : popup_list { key = \"s_jack\"; label = \"잭 종류:\"; width = 20; } " dcl-file)
      (write-line "      : toggle { key = \"s_chk_corbel_enable\"; label = \"까치발 생성\"; } " dcl-file)
      (write-line "    } " dcl-file)
      (write-line "    : row { " dcl-file)
      (write-line "      : popup_list { key = \"s_conn\"; label = \"까치발 연결 방식:\"; width = 30; } " dcl-file)
      (write-line "      : edit_box { key = \"s_corbel_dist\"; label = \"까치발 거리(m):\"; edit_width = 6; } " dcl-file)
      (write-line "    } " dcl-file)
      (write-line "    : row { alignment = right; " dcl-file)
      (write-line "      : button { key = \"s_btn_corbel_del\"; label = \"까치발 삭제\"; width = 14; } " dcl-file)
      (write-line "      : button { key = \"s_btn_corbel_reset\"; label = \"까치발 초기화\"; width = 14; } " dcl-file)
      (write-line "    } " dcl-file)
      (write-line "    : row { " dcl-file)
      (write-line "      : popup_list { key = \"s_jack_start_1h\"; label = \"1H 잭 시작(평면):\"; width = 26; } " dcl-file)
      (write-line "    } " dcl-file)
      (write-line "    : spacer { height = 0.5; } " dcl-file)
      (write-line "    : popup_list { key = \"s_start_mode\"; label = \"작도 시작 기준:\"; width = 30; } " dcl-file)
      (write-line "    : edit_box { key = \"s_ctc\"; label = \"배열 간격 (C.T.C, m, 직교기준):\"; edit_width = 10; } " dcl-file)
      (write-line "    : row { " dcl-file)
      (write-line "      : text { key = \"s_angle_info\"; label = \"버팀보 각도: 띠장 직교 (90.0°)\"; width = 26; } " dcl-file)
      (write-line "      : button { key = \"btn_angle_strut\"; label = \"각도 지정(끝점 클릭)\"; width = 18; } " dcl-file)
      (write-line "      : button { key = \"btn_angle_reset\"; label = \"90° 초기화\"; width = 10; } " dcl-file)
      (write-line "    } " dcl-file)
      (write-line "    : row { " dcl-file)
      (write-line "      : button { key = \"btn_draw_strut\"; label = \"도면에서 직접 작도\"; width = 24; } " dcl-file)
      (write-line "      : button { key = \"btn_add_subgroup\"; label = \"서브그룹 추가 작도 (Sub-group+)\"; width = 28; } " dcl-file)
      (write-line "    } " dcl-file)
      (write-line "    : spacer { height = 0.5; } " dcl-file)
      (write-line "    : boxed_column { label = \"보강재(Brace) 설정\"; " dcl-file)
      (write-line "      : toggle { key = \"s_chk_stiffener_enable\"; label = \"보강재(Brace) 생성 적용\"; } " dcl-file)
      (write-line "      : row { : text { label = \"설계 세장비 한계:\"; width = 16; } : popup_list { key = \"s_slenderness_limit\"; width = 20; } } " dcl-file)
      (write-line "      : text { key = \"s_stiffener_info\"; label = \"최대길이: 계산 대기 | 허용: 0.0m | 0등분 | 간격: 0.0m\"; alignment = centered; } " dcl-file)
      (write-line "      : row { : toggle { key = \"s_chk_manual_interval\"; label = \"수동 간격(m):\"; width = 16; } : edit_box { key = \"s_manual_interval\"; width = 10; } } " dcl-file)
      (write-line "      : row { : text { label = \"보강재 여유장(mm) :\"; width = 16; } : edit_box { key = \"s_stiffener_margin\"; width = 10; } } " dcl-file)
      (write-line "    } " dcl-file)
      (write-line "    : boxed_column { label = \"중간말뚝(Post pile) 설정\"; " dcl-file)
      (write-line "      : row { " dcl-file)
      (write-line "        : toggle { key = \"s_chk_post_enable\"; label = \"생성 적용\"; value = \"1\"; width = 12; } " dcl-file)
      (write-line "      } " dcl-file)
      (write-line "      : row { " dcl-file)
      (write-line "        : radio_row { key = \"s_post_side_grp\"; " dcl-file)
      (write-line "          : radio_button { key = \"s_post_side_L\"; label = \"보강재 왼쪽(Top)\"; value = \"1\"; } " dcl-file)
      (write-line "          : radio_button { key = \"s_post_side_R\"; label = \"보강재 오른쪽(Bottom)\"; } " dcl-file)
      (write-line "        } " dcl-file)
      (write-line "      } " dcl-file)
      (write-line "      : row { " dcl-file)
      (write-line "        : popup_list { key = \"s_post_pos_1h\"; label = \"1H 말뚝 위치:\"; width = 26; } " dcl-file)
      (write-line "      } " dcl-file)
      (write-line "      : row { alignment = right; " dcl-file)
      (write-line "        : button { key = \"s_btn_post_add\"; label = \"수동추가\"; width = 10; } " dcl-file)
      (write-line "        : button { key = \"s_btn_post_del\"; label = \"수동삭제\"; width = 10; } " dcl-file)
      (write-line "        : button { key = \"s_btn_post_reset\"; label = \"초기화\"; width = 10; } " dcl-file)
      (write-line "      } " dcl-file)
      (write-line "    } " dcl-file)
      (write-line "    : spacer { height = 1; } " dcl-file)
      (write-line "    : button { key = \"btn_redraw_strut\"; label = \"도면에서 확인/측정\"; } " dcl-file)
      (write-line "    : spacer { height = 1; } " dcl-file)
      (write-line "    : row { alignment = centered; " dcl-file)
      (write-line "      : button { key = \"accept\"; label = \"확인\"; is_default = true; width = 12; } " dcl-file)
      (write-line "      : button { key = \"cancel\"; label = \"취소\"; is_cancel = true; width = 12; } " dcl-file)
      (write-line "    } " dcl-file)
      (write-line "  } " dcl-file)
      (write-line "} " dcl-file)

      ;; ----------------------------------------------------------------------
      ;; [DCL 15] tsp_support_anchor : 앵커(Earth Anchor) 입력
      ;; ----------------------------------------------------------------------
      (write-line "tsp_support_anchor : dialog { label = \"앵커(Earth Anchor) 입력\"; " dcl-file)
      (write-line "  : column { " dcl-file)
      (write-line "    : row { " dcl-file)
      (write-line "      : edit_box { key = \"a_name\"; label = \"이름:\"; width = 15; } " dcl-file)
      (write-line "      : popup_list { key = \"a_shape\"; label = \"형상:\"; width = 15; } " dcl-file)
      (write-line "    } " dcl-file)
      (write-line "    : row { " dcl-file)
      (write-line "      : edit_box { key = \"a_depth\"; label = \"설치깊이(m):\"; width = 10; } " dcl-file)
      (write-line "      : edit_box { key = \"a_angle\"; label = \"설치각도(도):\"; width = 5; } " dcl-file)
      (write-line "    } " dcl-file)
      (write-line "    : row { " dcl-file)
      (write-line "      : edit_box { key = \"a_free\"; label = \"자유장(m):\"; width = 10; } " dcl-file)
      (write-line "      : edit_box { key = \"a_bond\"; label = \"정착장(m):\"; width = 10; } " dcl-file)
      (write-line "    } " dcl-file)
      (write-line "    : row { " dcl-file)
      (write-line "      : popup_list { key = \"a_mat\"; label = \"재질:\"; width = 15; } " dcl-file)
      (write-line "      : popup_list { key = \"a_sec\"; label = \"단면:\"; width = 20; } " dcl-file)
      (write-line "    } " dcl-file)
      (write-line "    : row { " dcl-file)
      (write-line "      : popup_list { key = \"a_wale_spec\"; label = \"앵커 띠장 규격:\"; width = 28; } " dcl-file)
      (write-line "    } " dcl-file)
      (write-line "    : spacer { height = 1; } " dcl-file)
      (write-line "    : row { alignment = centered; " dcl-file)
      (write-line "      : button { key = \"btn_adjust_plan_angle\"; label = \"평면 각도 조정\"; width = 18; } " dcl-file)
      (write-line "      : button { key = \"accept\"; label = \"확인\"; is_default = true; width = 12; } " dcl-file)
      (write-line "      : button { key = \"cancel\"; label = \"취소\"; is_cancel = true; width = 12; } " dcl-file)
      (write-line "    } " dcl-file)
      (write-line "  } " dcl-file)
      (write-line "} " dcl-file)

      ;; ----------------------------------------------------------------------
      ;; [DCL 16] tsp_csv_mapping : 데이터 세그먼트 매칭
      ;; ----------------------------------------------------------------------
      (write-line "tsp_csv_mapping : dialog { label = \"데이터 매칭 (Manual Mapping)\"; " dcl-file)
      (write-line "  : column { " dcl-file)
      (write-line "    : text { label = \"▶ 불러온 대상 데이터 목록 (매칭할 대상을 선택하세요)\"; } " dcl-file)
      (write-line "    : row { " dcl-file)
      (write-line "      : text { label = \"No.\"; width = 4; } " dcl-file)
      (write-line "      : text { label = \"이름\"; width = 10; } " dcl-file)
      (write-line "      : text { label = \"단면\"; width = 6; } " dcl-file)
      (write-line "      : text { label = \"흙막이벽\"; width = 12; } " dcl-file)
      (write-line "      : text { label = \"H-pile/띠장 규격\"; width = 28; } " dcl-file)
      (write-line "      : text { label = \"지보재\"; width = 15; } " dcl-file)
      (write-line "      : text { label = \"사보강재(Corner Strut)\"; width = 25; } " dcl-file)
      (write-line "      : text { label = \"굴착깊이\"; width = 10; } " dcl-file)
      (write-line "    } " dcl-file)
      (write-line "    : list_box { key = \"csv_list\"; width = 125; height = 12; fixed_width = true; fixed_height = true; multiple_select = false; tabs = \"5 15 21 33 60 75 105\"; } " dcl-file)
      (write-line "    : spacer { height = 0.5; } " dcl-file)
      (write-line "    : text { label = \"▶ 현재 도면 세그먼트에 매칭 (위 목록에서 선택 후 아래에 할당)\"; } " dcl-file)
      (write-line "    : list_box { key = \"map_list\"; width = 125; height = 10; fixed_width = true; fixed_height = true; multiple_select = false; tabs = \"30\"; } " dcl-file)
      (write-line "  } " dcl-file)
      (write-line "  : spacer { height = 0.5; } " dcl-file)
      (write-line "  : row { alignment = centered; " dcl-file)
      (write-line "    : button { key = \"btn_match\"; label = \"▼ 선택 항목 매칭 지정\"; width = 22; } " dcl-file)
      (write-line "    : button { key = \"btn_unmatch\"; label = \"매칭 해제\"; width = 15; } " dcl-file)
      (write-line "    : button { key = \"btn_auto\"; label = \"순차 자동 매칭\"; width = 20; } " dcl-file)
      (write-line "  } " dcl-file)
      (write-line "  : spacer { height = 0.5; } " dcl-file)
      (write-line "  : row { alignment = centered; " dcl-file)
      (write-line "    : button { key = \"accept\"; label = \"적용 (확인)\"; is_default = true; width = 15; } " dcl-file)
      (write-line "    : button { key = \"cancel\"; label = \"취소\"; is_cancel = true; width = 15; } " dcl-file)
      (write-line "  } " dcl-file)
      (write-line "} " dcl-file)

      (close dcl-file)
      dcl-path
    )
    nil
  )
)
