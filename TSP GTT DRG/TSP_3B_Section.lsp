;;; ==========================================================================
;;; 파일명: TSP_3B_Section.lsp
;;; 구  분: 단면도 및 지반 주상도 작도 (Part B)
;;; 역  할: 단면 띠장/유압잭/스크류잭 블록 정의, 지하수위 기호, 지반 주상도 및 N치 작도, H-Pile+토류판/CIP 수직 단면도, 단면 지보재/브래킷/숏크리트/그라우팅 작도 [draw-section-hpile]
;;; 포함 함수: draw-section-hpile
;;; --------------------------------------------------------------------------
;;; [안내] 이 파일은 TSP.lsp(메인 로더)에 의해 자동으로 로드되는 하위 모듈입니다.
;;;        코드 수정 시 전체 파일을 합칠 필요 없이 이 파일만 단독 패치하면 됩니다.
;;; ==========================================================================

;;;;==========================================================================
;;;; defun draw-section-hpile : 단면 H-Pile, 토류판, 띠장, 지보재(버팀보/잭/앵커), 숏크리트 등 통합 작도
;;;;==========================================================================
(defun draw-section-hpile (start-pt side h b tw tf max-depth embed-depth / layer-name total-len top-len inner-layer-name dir-x cx cy y-top y-bot x-tf exc-y pt-exc-start rock-depth found-rock timber-depth pt-timber-start pt-timber-end pt-timber-bottom-start pt-timber-bottom-end timber-pl hatch-obj sa doc mspace timber-bot-y col-x-pos rock-y pt-debug-start pt-debug-end pt-exc-end s-item s-type s-depth ins-y pt-ins s-ang s-free s-bond ang-rad draw-ang pt-free-end pt-bond-end wale-data wale-h wale-b wale-tw wale-tf wale-dir wale-offset wale-upper-y wale-lower-y wale-upper-insert-pt wale-lower-insert-pt shotcrete-bot-y pt-sc-start pt-sc-end pt-sc-bot-start pt-sc-bot-end sc-pl l-type wale-layer-name pt-ins-wale-base wale-rot-angle jack-block-name jack-insert-x pt-jack-ins jack-rot strut-start-x pt-strut-start strut-end-x pt-strut-end strut-h half-h strut-tf s-jack-type s-sec-str strut-data ep-thick ep-end-x stiff-x1 stiff-x2 brk-p1 brk-p2 brk-p3 brk-p4 p1-x p1-y pt-p1 p2-x p2-y pt-p2 pt-p1-h pt-p2-h face-ang pt-meet p-head-center p-head-1 p-head-2 p-head-3 p-head-4 out-ang pt-anchor-start x-left x-right water-lvl grout-dia grout-bot-y user-embed-mm x-grout-start x-grout-end p1 p2 p3 p4 grout-pl)

  (setq inner-layer-name (strcat "_H-Pile_" (itoa h) "x" (itoa b) "x" (itoa tw) "-" (itoa tf)))
  (create-layer-if-not-exists inner-layer-name "3")
  (create-layer-if-not-exists "_토류판(timber)" "1")
  (create-layer-if-not-exists "_앵커(Anchor)" "6")
  (create-layer-if-not-exists "_지반선" "8")
  (create-layer-if-not-exists "_숏크리트(shotcrete)" "7")
  (create-layer-if-not-exists "DEBUG_POINT_ANCHOR" "6")
  (create-layer-if-not-exists "DEBUG_POINT_STRUT" "2")
  (create-layer-if-not-exists "DEBUG_POINT_USER" "7")
  (create-layer-if-not-exists "DEBUG_POINT_HPILE" "4")

  (setq total-len (* (+ max-depth embed-depth) 1000.0))
  (setq top-len 500.0)
  (setq cx (car start-pt)) (setq cy (cadr start-pt))
  (entmake (list '(0 . "POINT") '(8 . "DEBUG_POINT_USER") '(62 . 7) (cons 10 start-pt)))

  (setq exc-y (- cy (* max-depth 1000.0)))
  (setq pt-exc-start (list cx exc-y 0.0))
  (entmake (list '(0 . "POINT") '(8 . "DEBUG_POINT_HPILE") '(62 . 4) (cons 10 pt-exc-start)))

  (if (= side "L")
    (setq pt-exc-end (polar pt-exc-start 0.0 30000.0))
    (setq pt-exc-end (polar pt-exc-start pi 30000.0))
  )
  (entmake (list '(0 . "LWPOLYLINE") '(100 . "AcDbEntity") '(100 . "AcDbPolyline") (cons 8 "_지반선") (cons 62 8) '(90 . 2) '(70 . 0) (cons 10 pt-exc-start) (cons 10 pt-exc-end)))

  (setq dir-x -1.0) (setq wale-dir 1.0)
  (if (= side "R") (progn (setq dir-x 1.0) (setq wale-dir -1.0)))
  (setq y-top (+ cy top-len)) (setq y-bot (- cy total-len))

  ;; 수직 H-Pile 작도 공용 함수 호출
  (setq x-left (min cx (+ cx (* h dir-x))))
  (setq x-right (max cx (+ cx (* h dir-x))))
  (draw-vertical-hpile x-left x-right y-top y-bot tf inner-layer-name)

  ;; 토류판 배치를 위한 1차 플랜지 기준 X좌표 산출
  (setq x-tf (+ cx (* tf dir-x)))

  (setq wale-data nil)
  (if (and *tsp-wale-spec* (= *tsp-wale-spec* "User-defined") *tsp-wale-custom*)
    (setq wale-data *tsp-wale-custom*)
    (setq wale-data (parse-h-spec *tsp-wale-spec*))
  )
  (if (null wale-data) (setq wale-data '(300 300 10 15)))
  (setq wale-h (nth 0 wale-data)) (setq wale-b (nth 1 wale-data)) (setq wale-tw (nth 2 wale-data)) (setq wale-tf (nth 3 wale-data))
  (setq wale-layer-name "_띠장(Wale)")
  (create-layer-if-not-exists wale-layer-name "3")
  (create-strut-jack-block)
  (create-strut-screw-jack-block)

  (if *tsp-support-list*
    (foreach s-item *tsp-support-list*
      (setq s-type (car s-item)) (setq s-depth (cadddr s-item))
      (setq ins-y (- cy (* s-depth 1000.0)))
      (setq pt-ins (list cx ins-y 0.0))
      ;; 각 지보재 단별 고유 띠장 규격 추출 (미지정 시 세그먼트 기본 띠장 사용)
      (setq wale-data (tsp-get-support-item-wale-vals s-item *tsp-wale-spec* *tsp-wale-custom*))
      (setq wale-h (nth 0 wale-data)) (setq wale-b (nth 1 wale-data)) (setq wale-tw (nth 2 wale-data)) (setq wale-tf (nth 3 wale-data))
      (cond
        ((wcmatch s-type "앵커*")
          (setq wale-rot-angle (* -0.5 pi wale-dir))
          (setq wale-offset (+ 150.0 (/ wale-b 2.0)))
          (setq wale-upper-insert-pt (list cx (+ ins-y wale-offset) 0.0))
          (draw-wale-section wale-upper-insert-pt wale-rot-angle wale-layer-name wale-h wale-b wale-tw wale-tf 0.0 0.0)
          (setq wale-lower-insert-pt (list cx (- ins-y wale-offset) 0.0))
          (draw-wale-section wale-lower-insert-pt wale-rot-angle wale-layer-name wale-h wale-b wale-tw wale-tf 0.0 0.0)
          (entmake (list '(0 . "POINT") '(8 . "DEBUG_POINT_ANCHOR") '(62 . 6) (cons 10 pt-ins)))
          (setq s-ang (nth 4 s-item)) (setq s-free (nth 5 s-item)) (setq s-bond (nth 6 s-item))
          (setq ang-rad (* s-ang (/ pi 180.0)))
          (if (= side "L") (setq draw-ang (+ pi ang-rad)) (setq draw-ang (- (* 2.0 pi) ang-rad)))
          (setq pt-free-end (polar pt-ins draw-ang (* s-free 1000.0)))
          (setq pt-bond-end (polar pt-free-end draw-ang (* s-bond 1000.0)))
          (setq out-ang (+ draw-ang pi))
          (setq p1-x (+ cx (* wale-h wale-dir)))
          (setq p1-y (+ ins-y wale-offset (/ wale-b 2.0)))
          (setq pt-p1 (list p1-x p1-y 0.0))
          (setq p2-x p1-x)
          (setq p2-y (- ins-y wale-offset (/ wale-b 2.0)))
          (setq pt-p2 (list p2-x p2-y 0.0))
          (setq pt-p1-h (list (+ p1-x (* 100.0 wale-dir)) p1-y 0.0))
          (setq pt-p2-h (list (+ p2-x (* 100.0 wale-dir)) p2-y 0.0))
          (setq face-ang (+ draw-ang (* wale-dir (/ pi 2.0))))
          (setq pt-meet (polar pt-p1-h face-ang 400.0))
          (entmake (list '(0 . "LWPOLYLINE") '(100 . "AcDbEntity") '(100 . "AcDbPolyline")
                         (cons 8 "_앵커(Anchor)") (cons 62 6) '(90 . 5) '(70 . 1)
                         (cons 10 pt-p1) (cons 10 pt-p1-h) (cons 10 pt-meet) (cons 10 pt-p2-h) (cons 10 pt-p2)))
          (setq p-head-center (inters pt-ins pt-free-end pt-p1-h pt-meet nil))
          (if (null p-head-center)
            (setq p-head-center (polar pt-p1-h (angle pt-p1-h pt-meet) 200.0))
          )
          (setq p-head-1 (polar p-head-center face-ang 100.0))
          (setq p-head-2 (polar p-head-center (+ face-ang pi) 100.0))
          (setq p-head-3 (polar p-head-2 out-ang 60.0))
          (setq p-head-4 (polar p-head-1 out-ang 60.0))
          (entmake (list '(0 . "LWPOLYLINE") '(100 . "AcDbEntity") '(100 . "AcDbPolyline")
                         (cons 8 "_앵커(Anchor)") (cons 62 6) '(90 . 4) '(70 . 1)
                         (cons 10 p-head-1) (cons 10 p-head-2) (cons 10 p-head-3) (cons 10 p-head-4)))
          (setq pt-anchor-start (polar p-head-center out-ang 210.0))
          (entmake (list '(0 . "LINE") (cons 8 "_앵커(Anchor)") (cons 62 6) (cons 10 pt-anchor-start) (cons 11 pt-ins)))
          (entmake (list '(0 . "LINE") (cons 8 "_앵커(Anchor)") (cons 62 6) (cons 10 pt-ins) (cons 11 pt-free-end)))
          (entmake (list '(0 . "LWPOLYLINE") '(100 . "AcDbEntity") '(100 . "AcDbPolyline") (cons 8 "_앵커(Anchor)") (cons 62 6) '(90 . 2) '(70 . 0) '(43 . 400.0) (cons 10 (list (car pt-free-end) (cadr pt-free-end))) (cons 10 (list (car pt-bond-end) (cadr pt-bond-end)))))
        )
        ((wcmatch s-type "버팀보*")
        ;; 단일 또는 2H(2겹 밀착) 띠장 및 보걸이 삽입
        (setq wale-rot-angle (* -0.5 pi wale-dir))
        (if (wcmatch (tsp-get-support-item-wale-spec s-item *tsp-wale-spec*) "2H *")
          (progn
            (draw-wale-section (list cx (+ ins-y (/ wale-b 2.0)) 0.0) wale-rot-angle wale-layer-name wale-h wale-b wale-tw wale-tf 0.0 0.0)
            (draw-wale-section (list cx (- ins-y (/ wale-b 2.0)) 0.0) wale-rot-angle wale-layer-name wale-h wale-b wale-tw wale-tf 0.0 0.0)
          )
          (draw-wale-section pt-ins wale-rot-angle wale-layer-name wale-h wale-b wale-tw wale-tf 0.0 0.0)
        )
          (setq s-jack-type (nth 7 s-item))
          (if (or (null s-jack-type) (= s-jack-type "")) (setq s-jack-type "스크류잭"))
          (if (equal s-jack-type "스크류잭")
            (setq jack-block-name "스크류잭")
            (setq jack-block-name "유압잭")
          )
          (setq jack-insert-x (+ cx (* wale-h wale-dir)))
          (setq pt-jack-ins (list jack-insert-x ins-y 0.0))
          (setq jack-rot (if (> wale-dir 0) 0.0 pi))
          (entmake (list '(0 . "INSERT")
                         (cons 2 jack-block-name)
                         (cons 8 (if (equal jack-block-name "스크류잭") "_스크류잭" "_유압잭"))
                         (cons 62 2)
                         (cons 10 pt-jack-ins)
                         '(41 . 1.0) '(42 . 1.0) '(43 . 1.0)
                         (cons 50 jack-rot)))
          (setq s-sec-str (nth 6 s-item))
          (setq strut-data (parse-h-spec s-sec-str))
          (if (null strut-data) (setq strut-data '(300 300 10 15)))
          (setq strut-h (nth 0 strut-data))
          (setq strut-tf (nth 3 strut-data))
          (setq half-h (/ strut-h 2.0))
          (setq y-top (+ ins-y half-h))
          (setq y-top-in (- y-top strut-tf))
          (setq y-bot (- ins-y half-h))
          (setq y-bot-in (+ y-bot strut-tf))
          (setq x-jack-end (+ jack-insert-x (* 583.0 wale-dir)))
          (setq ep-thick 14.0)
          (setq x-ep-end (+ x-jack-end (* ep-thick wale-dir)))
          (setq stiff-len 200.0)
          (setq stiff-thick 14.0)
          (setq x-stiff-end (+ x-ep-end (* stiff-len wale-dir)))
          (setq x-strut-end (+ x-ep-end (* 4000.0 wale-dir)))
          (entmake (list '(0 . "LWPOLYLINE") '(100 . "AcDbEntity") '(100 . "AcDbPolyline")
                         (cons 8 "_버팀보(Strut)") (cons 62 3) '(90 . 4) '(70 . 1)
                         (cons 10 (list x-jack-end y-top 0.0))
                         (cons 10 (list x-ep-end y-top 0.0))
                         (cons 10 (list x-ep-end y-bot 0.0))
                         (cons 10 (list x-jack-end y-bot 0.0))))
          (setq stiff-y-top (+ ins-y (/ stiff-thick 2.0)))
          (setq stiff-y-bot (- ins-y (/ stiff-thick 2.0)))
          (entmake (list '(0 . "LINE") (cons 8 "_버팀보(Strut)") (cons 62 3)
                         (cons 10 (list x-ep-end stiff-y-top 0.0)) (cons 11 (list x-stiff-end stiff-y-top 0.0))))
          (entmake (list '(0 . "LINE") (cons 8 "_버팀보(Strut)") (cons 62 3)
                         (cons 10 (list x-ep-end stiff-y-bot 0.0)) (cons 11 (list x-stiff-end stiff-y-bot 0.0))))
          (entmake (list '(0 . "LINE") (cons 8 "_버팀보(Strut)") (cons 62 3)
                         (cons 10 (list x-stiff-end stiff-y-top 0.0)) (cons 11 (list x-stiff-end stiff-y-bot 0.0))))
          (entmake (list '(0 . "LINE") (cons 8 "_버팀보(Strut)") (cons 62 3)
                         (cons 10 (list x-ep-end y-top 0.0)) (cons 11 (list x-strut-end y-top 0.0))))
          (entmake (list '(0 . "LINE") (cons 8 "_버팀보(Strut)") (cons 62 3)
                         (cons 10 (list x-ep-end y-bot 0.0)) (cons 11 (list x-strut-end y-bot 0.0))))
          (entmake (list '(0 . "LINE") (cons 8 "_버팀보(Strut)") (cons 62 1)
                         (cons 10 (list x-ep-end y-top-in 0.0)) (cons 11 (list x-strut-end y-top-in 0.0))))
          (entmake (list '(0 . "LINE") (cons 8 "_버팀보(Strut)") (cons 62 1)
                         (cons 10 (list x-ep-end y-bot-in 0.0)) (cons 11 (list x-strut-end y-bot-in 0.0))))
          (setq bulge-val (if (> wale-dir 0) 0.5 -0.5))
          (entmake (list '(0 . "LWPOLYLINE") '(100 . "AcDbEntity") '(100 . "AcDbPolyline")
                         (cons 8 "_버팀보(Strut)") (cons 62 1) '(90 . 5) '(70 . 0)
                         (cons 10 (list x-strut-end y-top 0.0))    (cons 42 0.0)
                         (cons 10 (list x-strut-end y-top-in 0.0)) (cons 42 bulge-val)
                         (cons 10 (list x-strut-end ins-y 0.0))    (cons 42 (- bulge-val))
                         (cons 10 (list x-strut-end y-bot-in 0.0)) (cons 42 0.0)
                         (cons 10 (list x-strut-end y-bot 0.0))))
        )
      )
    )
  )

  ;; 공용 함수를 이용하여 암반 심도 확보
  (setq rock-depth (tsp-get-rock-start-depth))

  (if rock-depth
    (if (>= rock-depth max-depth)
        (progn (setq timber-bot-y exc-y) (setq shotcrete-bot-y nil))
        (progn (setq timber-bot-y (- cy (* rock-depth 1000.0))) (setq shotcrete-bot-y exc-y))
    )
    (progn (setq timber-bot-y exc-y) (setq shotcrete-bot-y nil))
  )

  (setq pt-timber-start (list x-tf cy 0.0))
  (setq pt-timber-end (list (+ x-tf (* *tsp-timber-thickness* dir-x)) cy 0.0))
  (setq pt-timber-bottom-end (list (car pt-timber-end) timber-bot-y 0.0))
  (setq pt-timber-bottom-start (list (car pt-timber-start) timber-bot-y 0.0))
  (entmake (list '(0 . "LWPOLYLINE") '(100 . "AcDbEntity") '(100 . "AcDbPolyline") (cons 8 "_토류판(timber)") (cons 62 1) '(90 . 4) '(70 . 1) (cons 10 pt-timber-start) (cons 10 pt-timber-end) (cons 10 pt-timber-bottom-end) (cons 10 pt-timber-bottom-start)))
  (setq timber-pl (entlast))
  (setq doc (vla-get-activedocument (vlax-get-acad-object)))
  (if (= (getvar "CVPORT") 1)
    (setq mspace (vla-get-paperspace doc))
    (setq mspace (vla-get-modelspace doc))
  )
  (if timber-pl (progn
      (setq hatch-obj (vla-addhatch mspace 1 "ANSI31" :vlax-true))
      (vla-put-patternscale hatch-obj (* 100.0 (get-hatch-scale-factor)))
      (vla-put-patternangle hatch-obj (* 135.0 (/ pi 180.0)))
      (vla-put-layer hatch-obj "_토류판(timber)")
      (vla-put-color hatch-obj 1)
      (setq sa (vlax-make-safearray 9 (cons 0 0)))
      (vlax-safearray-fill sa (list (vlax-ename->vla-object timber-pl)))
      (vla-appendouterloop hatch-obj sa)
      (vla-evaluate hatch-obj)))

  ;; H-Pile+토류판 차수그라우팅 단면 작도 (지하수위가 굴착심도보다 위에 있고 그라우팅이 "없음(2)"이 아닐 때)
  (setq water-lvl 999.0)
  (if (and (boundp '*tsp-water-chk*) (= *tsp-water-chk* "1") (boundp '*tsp-water-depth*))
    (cond
      ((numberp *tsp-water-depth*) (setq water-lvl *tsp-water-depth*))
      ((= (type *tsp-water-depth*) 'STR) (setq water-lvl (atof *tsp-water-depth*)))
    )
  )
  (if (and (/= (if *tsp-cip-grouting-idx* *tsp-cip-grouting-idx* "0") "2") (> max-depth water-lvl))
    (progn
      (create-layer-if-not-exists "_그라우팅" "5")
      (setq grout-dia (if (and *tsp-cip-grouting-idx* (= *tsp-cip-grouting-idx* "1")) 600.0 200.0))
      (setq grout-bot-y y-bot)
      (if (and rock-depth (< rock-depth max-depth))
        (progn
          (setq user-embed-mm (if (and (boundp '*tsp-rock-embed*) *tsp-rock-embed* (/= *tsp-rock-embed* "")) (atof *tsp-rock-embed*) 500.0))
          (setq grout-bot-y (max exc-y (- (- cy (* rock-depth 1000.0)) user-embed-mm)))
        )
      )
      (setq x-grout-start (+ cx (* h dir-x)))
      (setq x-grout-end (+ x-grout-start (* grout-dia dir-x)))
      (setq p1 (list x-grout-end cy 0.0))
      (setq p2 (list x-grout-start cy 0.0))
      (setq p3 (list x-grout-start grout-bot-y 0.0))
      (setq p4 (list x-grout-end grout-bot-y 0.0))
      (entmake (list '(0 . "LWPOLYLINE") '(100 . "AcDbEntity") '(100 . "AcDbPolyline")
                     (cons 8 "_그라우팅") (cons 62 5) '(90 . 4) '(70 . 1)
                     (cons 10 p1) (cons 10 p2) (cons 10 p3) (cons 10 p4)))
      (setq grout-pl (entlast))
      (if grout-pl
        (progn
          (setq hatch-obj (vla-addhatch mspace 1 "AR-SAND" :vlax-true))
          (vla-put-patternscale hatch-obj (* 6.0 (get-hatch-scale-factor)))
          (vla-put-patternangle hatch-obj 0.0)
          (vla-put-layer hatch-obj "_그라우팅")
          (vla-put-color hatch-obj 5)
          (setq sa (vlax-make-safearray 9 (cons 0 0)))
          (vlax-safearray-fill sa (list (vlax-ename->vla-object grout-pl)))
          (vla-appendouterloop hatch-obj sa)
          (vla-evaluate hatch-obj)
        )
      )
    )
  )

  (if shotcrete-bot-y
    (progn
      (setq pt-sc-start (list cx timber-bot-y 0.0))
      (setq pt-sc-end (list (+ cx (* *tsp-shotcrete-thick* dir-x)) timber-bot-y 0.0))
      (setq pt-sc-bot-end (list (car pt-sc-end) shotcrete-bot-y 0.0))
      (setq pt-sc-bot-start (list (car pt-sc-start) shotcrete-bot-y 0.0))
      (entmake (list '(0 . "LWPOLYLINE") '(100 . "AcDbEntity") '(100 . "AcDbPolyline") (cons 8 "_숏크리트(shotcrete)") (cons 62 7) '(90 . 4) '(70 . 1) (cons 10 pt-sc-start) (cons 10 pt-sc-end) (cons 10 pt-sc-bot-end) (cons 10 pt-sc-bot-start)))
      (setq sc-pl (entlast))
      (if sc-pl (progn
          (setq hatch-obj (vla-addhatch mspace 1 "AR-CONC" :vlax-true))
          (vla-put-patternscale hatch-obj (* 2.0 (get-hatch-scale-factor)))
          (vla-put-patternangle hatch-obj 0.0)
          (vla-put-layer hatch-obj "_숏크리트(shotcrete)")
          (vla-put-color hatch-obj 7)
          (setq sa (vlax-make-safearray 9 (cons 0 0)))
          (vlax-safearray-fill sa (list (vlax-ename->vla-object sc-pl)))
          (vla-appendouterloop hatch-obj sa)
          (vla-evaluate hatch-obj)))
    )
  )
  (princ "\n단면 H-Pile 작도 완료.")
)
