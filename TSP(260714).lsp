;;; ==========================================================================
;;; TSP.lsp - Temporary Structure Plan (Integrated Version)
;;; ==========================================================================
(vl-load-com)
;;; ==========================================================================
;;; [SECTION 1] 전역 변수 및 설정 (Global Variables)
;;; ==========================================================================
;;; ==========================================================================
;;; [교체 변수] 사용자 정의 지층 해치 패턴(PAT) 데이터베이스 (총 16종)
;;; ==========================================================================
(setq *tsp-custom-pat-data*
  '(
    ("CH_"
     "*CH_, 압축성 높은 점토"
     "45,0,0,0,3.53553391"
     "45,0.4,0,0,3.53553391"
    )
    ("CL_"
     "*CL_, 압축성 낮은 점토"
     "45,0,0,0,3.53553391"
    )
    ("GC_"
     "*GC_, 점토질 자갈"
     "45,0,0,0,3.53553391"
     "0,-0.21,0.72,2.5,2.5,0.42,-4.58"
     "0,-0.45,0.6,2.5,2.5,0.9,-4.1"
     "0,-0.5763,0.48,2.5,2.5,1.1526,-3.8474"
     "0,-0.658,0.36,2.5,2.5,1.3159,-3.6841"
     "0,-0.7106,0.24,2.5,2.5,1.4211,-3.5789"
     "0,-0.7403,0.12,2.5,2.5,1.4807,-3.5193"
     "0,-0.75,0,2.5,2.5,1.5,-3.5"
     "0,-0.7403,-0.12,2.5,2.5,1.4807,-3.5193"
     "0,-0.7106,-0.24,2.5,2.5,1.4211,-3.5789"
     "0,-0.658,-0.36,2.5,2.5,1.3159,-3.6841"
     "0,-0.5763,-0.48,2.5,2.5,1.1526,-3.8474"
     "0,-0.45,-0.6,2.5,2.5,0.9,-4.1"
     "0,-0.21,-0.72,2.5,2.5,0.42,-4.58"
    )
    ("GM_"
     "*GM_, 실트질 자갈"
     "90,0,0,0,2.5"
     "0,-0.21,0.72,2.5,2.5,0.42,-4.58"
     "0,-0.45,0.6,2.5,2.5,0.9,-4.1"
     "0,-0.5763,0.48,2.5,2.5,1.1526,-3.8474"
     "0,-0.658,0.36,2.5,2.5,1.3159,-3.6841"
     "0,-0.7106,0.24,2.5,2.5,1.4211,-3.5789"
     "0,-0.7403,0.12,2.5,2.5,1.4807,-3.5193"
     "0,-0.75,0,2.5,2.5,1.5,-3.5"
     "0,-0.7403,-0.12,2.5,2.5,1.4807,-3.5193"
     "0,-0.7106,-0.24,2.5,2.5,1.4211,-3.5789"
     "0,-0.658,-0.36,2.5,2.5,1.3159,-3.6841"
     "0,-0.5763,-0.48,2.5,2.5,1.1526,-3.8474"
     "0,-0.45,-0.6,2.5,2.5,0.9,-4.1"
     "0,-0.21,-0.72,2.5,2.5,0.42,-4.58"
    )
    ("GP_"
     "*GP_, 입도 불량 자갈"
     "0,0,0,2.5,2.5,0.42,-4.58"
     "0,-0.24,-0.12,2.5,2.5,0.9,-4.1"
     "0,-0.3663,-0.24,2.5,2.5,1.1526,-3.8474"
     "0,-0.448,-0.36,2.5,2.5,1.3159,-3.6841"
     "0,-0.5006,-0.48,2.5,2.5,1.4211,-3.5789"
     "0,-0.5303,-0.6,2.5,2.5,1.4807,-3.5193"
     "0,-0.54,-0.72,2.5,2.5,1.5,-3.5"
     "0,-0.5303,-0.84,2.5,2.5,1.4807,-3.5193"
     "0,-0.5006,-0.96,2.5,2.5,1.4211,-3.5789"
     "0,-0.448,-1.08,2.5,2.5,1.3159,-3.6841"
     "0,-0.3663,-1.2,2.5,2.5,1.1526,-3.8474"
     "0,-0.24,-1.32,2.5,2.5,0.9,-4.1"
     "0,0,-1.44,2.5,2.5,0.42,-4.58"
     "63.43494882,2.91,4.08,4.47213596,2.23606798,0.2236068,-10.95673309"
     "26.56505118,2.71,3.98,6.70820393,2.23606798,0.2236068,-10.95673309"
     "333.43494882,2.51,4.08,4.47213596,2.23606798,0.2236068,-10.95673309"
     "296.56505118,2.41,4.28,6.70820393,2.23606797,0.2236068,-10.95673309"
     "153.43494882,0.41,1.98,4.47213595,2.23606797,0.2236068,-10.95673309"
     "116.56505118,0.51,1.78,6.70820393,2.23606798,0.2236068,-10.95673309"
     "63.43494882,0.41,1.58,4.47213596,2.23606798,0.2236068,-10.95673309"
     "26.56505118,0.21,1.48,6.70820393,2.23606798,0.2236068,-10.95673309"
     "243.43494882,2.51,-0.52,4.47213596,2.23606798,0.2236068,-10.95673309"
     "206.56505118,2.71,-0.42,6.70820393,2.23606797,0.2236068,-10.95673309"
     "153.43494882,2.91,-0.52,4.47213595,2.23606797,0.2236068,-10.95673309"
     "116.56505118,3.01,-0.72,6.70820393,2.23606798,0.2236068,-10.95673309"
     "333.43494882,5.01,1.58,4.47213596,2.23606798,0.2236068,-10.95673309"
     "296.56505118,4.91,1.78,6.70820393,2.23606797,0.2236068,-10.95673309"
     "243.43494882,5.01,1.98,4.47213596,2.23606798,0.2236068,-10.95673309"
     "206.56505118,5.21,2.08,6.70820393,2.23606797,0.2236068,-10.95673309"
    )
    ("GW_"
     "*GW_, 입도 양호 자갈"
     "189.46232221,0,0,25.48184303,0.82199494,0.30413812,-30.10967452"
     "210.96375653,-0.3,-0.05,18.00735144,0.85749293,0.2915476,-28.86321188"
     "239.03624347,-0.55,-0.2,11.14740804,0.85749292,0.2915476,-28.86321188"
     "260.53767779,-0.7,-0.45,4.93196962,0.82199494,0.30413813,-30.10967453"
     "279.46232221,-0.75,-0.75,25.48184303,0.82199494,0.30413812,-30.10967452"
     "300.96375653,-0.7,-1.05,18.00735144,0.85749292,0.2915476,-28.86321188"
     "329.03624347,-0.55,-1.3,11.14740804,0.85749292,0.2915476,-28.86321188"
     "350.53767779,-0.3,-1.45,4.93196962,0.82199493,0.30413813,-30.10967453"
     "9.46232221,0,-1.5,25.48184303,0.82199494,0.30413812,-30.10967452"
     "30.96375653,0.3,-1.45,18.00735144,0.85749293,0.29154759,-28.86321188"
     "59.03624347,0.55,-1.3,11.14740804,0.85749292,0.2915476,-28.86321188"
     "80.53767779,0.7,-1.05,4.93196962,0.82199494,0.30413812,-30.10967452"
     "99.46232221,0.75,-0.75,25.48184303,0.82199494,0.30413812,-30.10967452"
     "120.96375653,0.7,-0.45,18.00735144,0.85749292,0.2915476,-28.86321188"
     "149.03624347,0.55,-0.2,11.14740804,0.85749292,0.2915476,-28.86321188"
     "170.53767779,0.3,-0.05,4.93196962,0.82199493,0.30413812,-30.10967452"
     "99.46232221,-1.75,-3.25,25.48184303,0.82199494,0.30413812,-30.10967452"
     "120.96375653,-1.8,-2.95,18.00735144,0.85749292,0.2915476,-28.86321188"
     "149.03624347,-1.95,-2.7,11.14740804,0.85749292,0.2915476,-28.86321188"
     "170.53767779,-2.2,-2.55,4.93196962,0.82199493,0.30413812,-30.10967452"
     "9.46232221,-2.5,1,25.48184303,0.82199494,0.30413812,-30.10967452"
     "30.96375653,-2.2,1.05,18.00735144,0.85749293,0.29154759,-28.86321188"
     "59.03624347,-1.95,1.2,11.14740804,0.85749292,0.2915476,-28.86321188"
     "80.53767779,-1.8,1.45,4.93196962,0.82199494,0.30413812,-30.10967452"
     "279.46232221,1.75,1.75,25.48184303,0.82199494,0.30413812,-30.10967452"
     "300.96375653,1.8,1.45,18.00735144,0.85749292,0.2915476,-28.86321188"
     "329.03624347,1.95,1.2,11.14740804,0.85749292,0.2915476,-28.86321188"
     "350.53767779,2.2,1.05,4.93196962,0.82199493,0.30413813,-30.10967453"
     "189.46232221,2.5,-2.5,25.48184303,0.82199494,0.30413812,-30.10967452"
     "210.96375653,2.2,-2.55,18.00735144,0.85749293,0.2915476,-28.86321188"
     "239.03624347,1.95,-2.7,11.14740804,0.85749292,0.2915476,-28.86321188"
     "260.53767779,1.8,-2.95,4.93196962,0.82199494,0.30413813,-30.10967453"
     "63.43494882,0.2,1.55,4.47213596,2.23606798,0.2236068,-10.95673309"
     "26.56505118,0,1.45,6.70820393,2.23606798,0.2236068,-10.95673309"
     "333.43494882,-0.2,1.55,4.47213596,2.23606798,0.2236068,-10.95673309"
     "296.56505118,-0.3,1.75,6.70820393,2.23606797,0.2236068,-10.95673309"
     "153.43494882,-2.3,-0.55,4.47213595,2.23606797,0.2236068,-10.95673309"
     "116.56505118,-2.2,-0.75,6.70820393,2.23606798,0.2236068,-10.95673309"
     "63.43494882,-2.3,-0.95,4.47213596,2.23606798,0.2236068,-10.95673309"
     "26.56505118,-2.5,-1.05,6.70820393,2.23606798,0.2236068,-10.95673309"
     "243.43494882,-0.2,-3.05,4.47213596,2.23606798,0.2236068,-10.95673309"
     "206.56505118,0,-2.95,6.70820393,2.23606797,0.2236068,-10.95673309"
     "153.43494882,0.2,-3.05,4.47213595,2.23606797,0.2236068,-10.95673309"
     "116.56505118,0.3,-3.25,6.70820393,2.23606798,0.2236068,-10.95673309"
     "333.43494882,2.3,-0.95,4.47213596,2.23606798,0.2236068,-10.95673309"
     "296.56505118,2.2,-0.75,6.70820393,2.23606797,0.2236068,-10.95673309"
     "243.43494882,2.3,-0.55,4.47213596,2.23606798,0.2236068,-10.95673309"
     "206.56505118,2.5,-0.45,6.70820393,2.23606797,0.2236068,-10.95673309"
    )
    ("HR_"
     "*HR_, 경암"
     "0,0,0,2.5,2.5,1.5,-3.5"
     "90,0.75,-0.75,2.5,2.5,1.5,-3.5"
    )
    ("MH_"
     "*MH_, 압축성 높은 실트"
     "90,0,0,0,2.5"
     "90,0.4,0,0,2.5"
    )
    ("ML_"
     "*ML_, 압축성 낮은 실트"
     "90,0,0,0,2.5"
    )
    ("RS_"
     "*RS_, 풍화토"
     "45,0,0,0.1767767,0.1767767"
     "45,0.01414,-0.01414,0.1767767,0.1767767"
     "0,0.0175,0.1725,0.125,0.125,0.06,-0.19"
     "90,0.0475,0.1425,0.125,0.125,0.06,-0.19"
     "45,-0.01415,0.01414,0.1767767,0.1767767"
    )
    ("SC_"
     "*SC_, 점토질 모래"
     "45,0,0,0,3.53553391"
     "0,-0.2062,0.4,2.5,2.5,0.4123,-4.5877"
     "0,-0.3354,0.3,2.5,2.5,0.6708,-4.3292"
     "0,-0.4031,0.2,2.5,2.5,0.8062,-4.1938"
     "0,-0.4387,0.1,2.5,2.5,0.8775,-4.1225"
     "0,-0.45,0,2.5,2.5,0.9,-4.1"
     "0,-0.4387,-0.1,2.5,2.5,0.8775,-4.1225"
     "0,-0.4031,-0.2,2.5,2.5,0.8062,-4.1938"
     "0,-0.3354,-0.3,2.5,2.5,0.6708,-4.3292"
     "0,-0.2062,-0.4,2.5,2.5,0.4123,-4.5877"
    )
    ("SM_"
     "*SM_, 실트질 모래"
     "90,0,0,0,2.5"
     "0,-0.2062,0.4,2.5,2.5,0.4123,-4.5877"
     "0,-0.3354,0.3,2.5,2.5,0.6708,-4.3292"
     "0,-0.4031,0.2,2.5,2.5,0.8062,-4.1938"
     "0,-0.4387,0.1,2.5,2.5,0.8775,-4.1225"
     "0,-0.45,0,2.5,2.5,0.9,-4.1"
     "0,-0.4387,-0.1,2.5,2.5,0.8775,-4.1225"
     "0,-0.4031,-0.2,2.5,2.5,0.8062,-4.1938"
     "0,-0.3354,-0.3,2.5,2.5,0.6708,-4.3292"
     "0,-0.2062,-0.4,2.5,2.5,0.4123,-4.5877"
    )
    ("SP_"
     "*SP_, 입도 불량 모래"
     "0,0,0,2.5,2.5,0.4123,-4.5877"
     "0,-0.1292,-0.1,2.5,2.5,0.6708,-4.3292"
     "0,-0.1969,-0.2,2.5,2.5,0.8062,-4.1938"
     "0,-0.2325,-0.3,2.5,2.5,0.8775,-4.1225"
     "0,-0.2438,-0.4,2.5,2.5,0.9,-4.1"
     "0,-0.2325,-0.5,2.5,2.5,0.8775,-4.1225"
     "0,-0.1969,-0.6,2.5,2.5,0.8062,-4.1938"
     "0,-0.1292,-0.7,2.5,2.5,0.6708,-4.3292"
     "0,0,-0.8,2.5,2.5,0.4123,-4.5877"
    )
    ("SR_"
     "*SR_, 연암"
     "0,0,0,2.5,2.5,1.5,-3.5"
     "90,0.75,-0.75,2.5,2.5,1.5,-3.5"
     "45,-1.75,0,0,3.53553391"
    )
    ("SW_"
     "*SW_, 입도 양호 모래"
     "206.56505118,0,0,6.70820393,2.23606797,0.3354102,-10.84492969"
     "153.43494882,0.3,-0.15,4.47213595,2.23606797,0.3354102,-10.84492969"
     "116.56505118,0.45,-0.45,6.70820393,2.23606798,0.3354102,-10.84492969"
     "63.43494882,0.3,-0.75,4.47213596,2.23606798,0.33541019,-10.84492969"
     "26.56505118,0,-0.9,6.70820393,2.23606798,0.3354102,-10.84492969"
     "333.43494882,-0.3,-0.75,4.47213596,2.23606798,0.3354102,-10.84492969"
     "296.56505118,-0.45,-0.45,6.70820393,2.23606797,0.3354102,-10.84492969"
     "243.43494882,-0.3,-0.15,4.47213596,2.23606798,0.3354102,-10.84492969"
     "153.43494882,-2.2,-2.65,4.47213595,2.23606797,0.3354102,-10.84492969"
     "116.56505118,-2.05,-2.95,6.70820393,2.23606798,0.3354102,-10.84492969"
     "63.43494882,-2.2,1.75,4.47213596,2.23606798,0.33541019,-10.84492969"
     "26.56505118,-2.5,1.6,6.70820393,2.23606798,0.3354102,-10.84492969"
     "333.43494882,2.2,1.75,4.47213596,2.23606798,0.3354102,-10.84492969"
     "296.56505118,2.05,2.05,6.70820393,2.23606797,0.3354102,-10.84492969"
     "243.43494882,2.2,-2.65,4.47213596,2.23606798,0.3354102,-10.84492969"
     "206.56505118,2.5,-2.5,6.70820393,2.23606797,0.3354102,-10.84492969"
    )
    ("WR_"
     "*WR_, 풍화암"
     "0,0,0,2.5,2.5,1.5,-3.5"
     "90,0.75,-0.75,2.5,2.5,1.5,-3.5"
     "45,-1.95,0,0,3.53553391"
     "45,-1.55,0,0,3.53553391"
    )
  )
)
;;; 표준 규격 리스트 중앙 관리
(setq *tsp-std-wall-list* '(
  "H 250×250×9/14"      ; 0
  "H 298×201×9/14"      ; 1
  "H 300×300×10/15"    ; 2
  "H 350×350×12/19"
  "H 400×400×13/21"
))
(setq *tsp-std-strut-list* '(
  "H 250×250×9/14"
  "H 298×201×9/14"
  "H 300×300×10/15"
  "H 350×350×12/19"
  "H 400×400×13/21"
))
;;; 1.1 H-Pile 및 띠장(Wale) 규격 변수
;;; (기본값 설정: 리스트의 인덱스를 사용하여 안전하게 가져옴)
(setq *tsp-hpile-spec* (nth 2 *tsp-std-wall-list*))     ; 기본값: H 300
(setq *tsp-hpile-custom* '(300 300 10 15))
(setq *tsp-wale-spec* (nth 2 *tsp-std-wall-list*))      ; 기본값: H 300
(setq *tsp-wale-custom* '(300 300 10 15))
;; 1.14 벽체 공법 타입 변수
;; [1단계 고정] 기본값은 항상 "HPILE", C.I.P는 사용자가 최종 확정 시에만 "CIP"로 변경됨
(setq *tsp-wall-type* "HPILE")      ; 벽체 공법 타입 기본값 ("HPILE" or "CIP")
;; 1.15 C.I.P 흙막이벽 전용 설정 변수
(setq *tsp-cip-max-depth* "10.0")   ; 최대 굴착 깊이
(setq *tsp-cip-embed-depth* "3.0")  ; 근입 깊이
(setq *tsp-cip-hpile-idx* "2")      ; H-Pile 규격 인덱스 (기본값: H 300)
(setq *tsp-cip-wale-idx* "2")       ; 띠장(Wale) 규격 인덱스 (기본값: H 300)
(setq *tsp-cip-dia* "500")          ; C.I.P 직경 기본값 (D500)
(setq *tsp-cip-mode-idx* "0")       ; 배열 모드 (0: 맞닿음/Tangent, 1: 겹침/Secant)
(setq *tsp-cip-overlap* "0")        ; 겹침량 기본값
(setq *tsp-cip-interval-idx* "2")   ; H-Pile 삽입 간격 (0: 1/1, 1: 1/2, 2: 2공건너 삽입)
(setq *tsp-cip-grouting-idx* "0")   ; 그라우팅 선택 (0: D200, 1: D600)
;;; 1.2 배치 및 굴착 설정 변수
(setq *tsp-ctc* 2.0)                                ; C.T.C 간격 (m)
(setq *tsp-timber-thickness* 60)                ; 토류판 두께 (mm)
(setq *tsp-max-excavation-depth* 10.0)       ; 최대 굴착 깊이 (m)
(setq *tsp-embedment-depth* 3.0)             ; 근입 깊이 (m)
;;; 1.3 지반 및 수위 변수
;;; 저장 형식: (이름 깊이 해치패턴 해치축척 해치각도 종류명 내부마찰각)
(setq *tsp-soil-layers* '())
(setq *tsp-water-chk* "0")                   ; 지하수위 체크 여부 ("0"=Off, "1"=On)
(setq *tsp-water-depth* 0.0)                 ; 지하수위 깊이 (m)
(setq *tsp-shotcrete-enable* "1")            ; 숏크리트 생성 마스터 스위치 ("0"=Off, "1"=On)
(setq *tsp-shotcrete-chk* "0")               ; 숏크리트 암반 선택 여부 ("0"=Off, "1"=On)
(setq *tsp-shotcrete-layer* "")              ; 숏크리트 시작 지정 암반층 이름
(setq *tsp-shotcrete-thick* 0.0)             ; 숏크리트 두께 T(mm)
;;; 1.4 지보재 변수
(setq *tsp-support-list* '())
;;; 1.5 도면 스케일 변수
(setq *tsp-scale-section* 200)               ; 단면도 스케일 (기본 1/200)
(setq *tsp-scale-plan* 600)                  ; 평면도 스케일 (기본 1/600)
;;; 1.6 프로젝트 관리 변수
(setq *tsp-current-project-name* "")         ; 현재 프로젝트 이름
(setq *tsp-data-dict-name* "TSP_DATA_DICT")  ; 딕셔너리 저장소 이름
;;; 1.7 변경 사항 감지 플래그
(setq *tsp-data-dirty* nil)                  ; 데이터 변경 여부 (T=변경됨, nil=변경없음)


;;; ==========================================================================
;;; [SECTION 2] 공통 유틸리티 (Common Utilities)
;;; ==========================================================================


;;;;==========================================================================
;;;; defun get-hatch-scale-factor : 도면의 MEASUREMENT 변수(0=Imperial, 1=Metric)에 따라 해치 스케일 보정값 반환
;;;;==========================================================================
(defun get-hatch-scale-factor ()
  (if (= (getvar "MEASUREMENT") 0)
    25.4  ;; Imperial 도면이면 25.4배 확대 (mm 단위처럼 보이게 보정)
    1.0   ;; Metric 도면이면 그대로 사용
  )
)


;;;;==========================================================================
;;;; defun create-layer-if-not-exists : 레이어가 존재하지 않으면 지정된 색상으로 생성
;;;;==========================================================================
(defun create-layer-if-not-exists (layer-name color / )
  (if (not (tblsearch "LAYER" layer-name))
    (command "._LAYER" "_M" layer-name "_C" color layer-name "")
  )
)


;;;;==========================================================================
;;;; defun is-numeric : 문자열이 숫자로 변환 가능한지 확인 (True/False)
;;;;==========================================================================
(defun is-numeric (str / result)
  (setq result T)
  (if (or (null str) (= str ""))
    (setq result nil)
    (if (not (numberp (read str)))
      (setq result nil)
    )
  )
  result
)


;;;;==========================================================================
;;;; defun parse-h-spec : "H 298x201..." 형식의 문자열을 파싱하여 리스트 (298 201...)로 변환
;;;;==========================================================================
(defun parse-h-spec (spec-str / clean-str i ch result-str)
  (if (and spec-str (wcmatch spec-str "H *"))
    (progn
      (setq clean-str (substr spec-str 3))
      (setq result-str "")
      (setq i 1)
      (while (<= i (strlen clean-str))
        (setq ch (substr clean-str i 1))
        (cond
          ((and (>= (ascii ch) 48) (<= (ascii ch) 57))
           (setq result-str (strcat result-str ch)))
          (t
           (if (> (strlen result-str) 0)
             (if (/= (substr result-str (strlen result-str) 1) " ")
               (setq result-str (strcat result-str " "))
             )
           ))
        )
        (setq i (1+ i))
      )
      (read (strcat "(" result-str ")"))
    )
    nil
  )
)


;;;;==========================================================================
;;;; defun format-depth-text : 깊이 값을 소수점 1자리 문자열로 포맷팅 (ex: "5.0")
;;;;==========================================================================
(defun format-depth-text (depth / str)
  (setq str (rtos depth 2 1))
  (if (not (vl-string-search "." str))
    (setq str (strcat str ".0"))
  )
  str
)


;;;;==========================================================================
;;;; defun tsp-get-project-list : 저장된 프로젝트 목록 반환 (직접 순회 방식)
;;;;==========================================================================
(defun tsp-get-project-list (/ proj-list dict-name raw-data item key)
  (setq dict-name "TSP_DATA_DICT")
  (setq proj-list '())
  ;; 1. 딕셔너리의 전체 데이터를 리스트로 가져옴
  (setq raw-data (vlax-ldata-list dict-name))
  ;; 2. 데이터가 존재하면 키(Project Name)만 추출
  (if raw-data
    (foreach item raw-data
      (setq key (car item)) ; dotted pair의 앞부분(key) 추출
      (if (= (type key) 'STR) ; 키가 문자열인 경우만 추가
        (setq proj-list (append proj-list (list key)))
      )
    )
  )
  proj-list
)


;;;;==========================================================================
;;;; defun tsp-generate-default-project-name : 중복되지 않는 다음 프로젝트 이름 생성 (Project_N+1)
;;;;==========================================================================
(defun tsp-generate-default-project-name (/ proj-list max-num curr-num name upper-name)
  (setq proj-list (tsp-get-project-list))
  (setq max-num 0)
  ;; 기존 목록에서 번호 파싱
  (foreach name proj-list
    (setq upper-name (strcase name))
    ;; "PROJECT_" 로 시작하는지 확인 (와일드카드 매칭)
    (if (wcmatch upper-name "PROJECT_*")
      (progn
        ;; "PROJECT_" 글자수(8) 다음부터 숫자 추출
        ;; 문자열이 "PROJECT_10" 이면 substr 9부터가 "10"
        (setq curr-num (atoi (substr upper-name 9)))
        (if (> curr-num max-num) (setq max-num curr-num))
      )
    )
  )
  ;; 가장 큰 번호 + 1 반환
  (strcat "Project_" (itoa (1+ max-num)))
)


;;;;==========================================================================
;;;; defun tsp-save-project-data : 프로젝트 데이터 저장
;;;;==========================================================================
(defun tsp-save-project-data (proj-name / data-pack dict-name)
  (setq dict-name "TSP_DATA_DICT")
  ;; 입력된 이름이 없으면 자동 생성
  (if (or (= proj-name "") (= proj-name nil))
    (setq proj-name (tsp-generate-default-project-name))
  )
  ;; 저장할 데이터 패키징
  (setq data-pack (list
        *segment-list*
        *tsp-hpile-spec*
        *tsp-hpile-custom*
        *tsp-wale-spec*
        *tsp-wale-custom*
        *tsp-ctc*
        *tsp-timber-thickness*
        *tsp-max-excavation-depth*
        *tsp-embedment-depth*
        *tsp-soil-layers*
        *tsp-water-chk*
        *tsp-water-depth*
        *tsp-support-list*
        *tsp-scale-section*
        *tsp-scale-plan*
        (if (vlax-ldata-get "TSP_DICT" "DELETED_POSTS") (vlax-ldata-get "TSP_DICT" "DELETED_POSTS") '())
        (if (vlax-ldata-get "TSP_DICT" "ADDED_POSTS") (vlax-ldata-get "TSP_DICT" "ADDED_POSTS") '())
      ))
  ;; ldata에 저장 수행
  (vlax-ldata-put dict-name proj-name data-pack)
  (setq *tsp-current-project-name* proj-name)
  (princ (strcat "\n[시스템] 프로젝트 '" proj-name "' 이(가) 도면에 저장되었습니다."))
  proj-name
)


;;;;==========================================================================
;;;; defun tsp-load-project-data : 데이터 불러오기  (형상일치 검증 및 좌표 보호)
;;;;==========================================================================
(defun tsp-load-project-data (proj-name / data-pack dict-name saved-segments curr-len saved-len i curr-seg saved-seg shape-match curr-len-val saved-len-val curr-ang-val saved-ang-val merged-seg merged-list)
  (setq dict-name "TSP_DATA_DICT")
  (setq data-pack (vlax-ldata-get dict-name proj-name))
  (if data-pack
    (progn
      (setq saved-segments (nth 0 data-pack))
      (setq curr-len (length *segment-list*))
      (setq saved-len (length saved-segments))
      (if (/= curr-len saved-len)
        (progn
          (alert (strcat "현재 경계선과 저장된 프로젝트의 세그먼트 개수가 달라 불러올 수 없습니다.\n\n- 현재 선분 수: " (itoa curr-len) "개\n- 저장된 선분 수: " (itoa saved-len) "개"))
          nil
        )
        (progn
          (setq shape-match T)
          (setq i 0)
          (while (and (< i curr-len) shape-match)
            (setq curr-seg (nth i *segment-list*))
            (setq saved-seg (nth i saved-segments))
            (setq curr-len-val (cdr (assoc 'LENGTH curr-seg)))
            (setq saved-len-val (cdr (assoc 'LENGTH saved-seg)))
            (setq curr-ang-val (cdr (assoc 'ANGLE curr-seg)))
            (setq saved-ang-val (cdr (assoc 'ANGLE saved-seg)))
            (if (or (not (equal curr-len-val saved-len-val 0.1))
                    (not (equal curr-ang-val saved-ang-val 0.1)))
              (setq shape-match nil)
            )
            (setq i (1+ i))
          )
          (if (not shape-match)
            (progn
              (alert "경계선의 형상(각 선분의 길이 또는 꺾임 각도)이 일치하지 않아 불러올 수 없습니다.\n\n정확히 동일한 형태의 경계선에서만 불러오기가 가능합니다.")
              nil
            )
            (progn
              (setq merged-list '())
              (setq i 0)
              (while (< i curr-len)
                (setq curr-seg (nth i *segment-list*))
                (setq saved-seg (nth i saved-segments))
                (setq merged-seg (list
                  (cons 'ID (cdr (assoc 'ID curr-seg)))
                  (cons 'NAME (cdr (assoc 'NAME saved-seg)))
                  (cons 'IS-DEFINED (cdr (assoc 'IS-DEFINED saved-seg)))
                  (cons 'SECTION-DRAW (cdr (assoc 'SECTION-DRAW saved-seg)))
                  (cons 'SOIL-DATA (cdr (assoc 'SOIL-DATA saved-seg)))
                  (cons 'WALL-SPEC (cdr (assoc 'WALL-SPEC saved-seg)))
                  (cons 'WALL-CUSTOM (cdr (assoc 'WALL-CUSTOM saved-seg)))
                  (cons 'WALE-SPEC (cdr (assoc 'WALE-SPEC saved-seg)))
                  (cons 'WALE-CUSTOM (cdr (assoc 'WALE-CUSTOM saved-seg)))
                  (cons 'CTC (cdr (assoc 'CTC saved-seg)))
                  (cons 'TIMBER-THICKNESS (cdr (assoc 'TIMBER-THICKNESS saved-seg)))
                  (cons 'MAX-DEPTH (cdr (assoc 'MAX-DEPTH saved-seg)))
                  (cons 'EMBED-DEPTH (cdr (assoc 'EMBED-DEPTH saved-seg)))
                  (cons 'WATER-CHK (cdr (assoc 'WATER-CHK saved-seg)))
                  (cons 'WATER-DEPTH (cdr (assoc 'WATER-DEPTH saved-seg)))
                  (cons 'SHOTCRETE-ENABLE (cdr (assoc 'SHOTCRETE-ENABLE saved-seg)))
                  (cons 'SHOTCRETE-CHK (cdr (assoc 'SHOTCRETE-CHK saved-seg)))
                  (cons 'SHOTCRETE-LAYER (cdr (assoc 'SHOTCRETE-LAYER saved-seg)))
                  (cons 'SHOTCRETE-THICK (cdr (assoc 'SHOTCRETE-THICK saved-seg)))
                  (cons 'SUPPORT-LIST (tsp-sanitize-support-list (cdr (assoc 'SUPPORT-LIST saved-seg))))
                  (cons 'CORNER-BRACE (cdr (assoc 'CORNER-BRACE saved-seg)))
                  (cons 'UPGRADE-WALE (cdr (assoc 'UPGRADE-WALE saved-seg)))
                  (cons 'WALL-TYPE (cdr (assoc 'WALL-TYPE saved-seg)))
                  (cons 'CIP-MAX-DEPTH (cdr (assoc 'CIP-MAX-DEPTH saved-seg)))
                  (cons 'CIP-EMBED-DEPTH (cdr (assoc 'CIP-EMBED-DEPTH saved-seg)))
                  (cons 'CIP-HPILE-IDX (cdr (assoc 'CIP-HPILE-IDX saved-seg)))
                  (cons 'CIP-WALE-IDX (cdr (assoc 'CIP-WALE-IDX saved-seg)))
                  (cons 'CIP-DIA (cdr (assoc 'CIP-DIA saved-seg)))
                  (cons 'CIP-MODE-IDX (cdr (assoc 'CIP-MODE-IDX saved-seg)))
                  (cons 'CIP-OVERLAP (cdr (assoc 'CIP-OVERLAP saved-seg)))
                  (cons 'CIP-EQUAL-DIVIDE (cdr (assoc 'CIP-EQUAL-DIVIDE saved-seg)))
                  (cons 'CIP-INTERVAL-IDX (cdr (assoc 'CIP-INTERVAL-IDX saved-seg)))
                  (cons 'CIP-GROUTING-IDX (cdr (assoc 'CIP-GROUTING-IDX saved-seg)))
                  ;; ---------------------------------------------------------
                  (cons 'V-START (cdr (assoc 'V-START curr-seg)))
                  (cons 'V-END (cdr (assoc 'V-END curr-seg)))
                  (cons 'ANGLE (cdr (assoc 'ANGLE curr-seg)))
                  (cons 'LENGTH (cdr (assoc 'LENGTH curr-seg)))
                ))
                (setq merged-list (append merged-list (list merged-seg)))
                (setq i (1+ i))
              )
              (setq *segment-list* merged-list)
              (setq *tsp-hpile-spec* (nth 1 data-pack))
              (setq *tsp-hpile-custom* (nth 2 data-pack))
              (setq *tsp-wale-spec* (nth 3 data-pack))
              (setq *tsp-wale-custom* (nth 4 data-pack))
              (setq *tsp-ctc* (nth 5 data-pack))
              (setq *tsp-timber-thickness* (nth 6 data-pack))
              (setq *tsp-max-excavation-depth* (nth 7 data-pack))
              (setq *tsp-embedment-depth* (nth 8 data-pack))
              (setq *tsp-soil-layers* (nth 9 data-pack))
              (setq *tsp-water-chk* (nth 10 data-pack))
              (setq *tsp-water-depth* (nth 11 data-pack))
              (setq *tsp-support-list* (tsp-sanitize-support-list (nth 12 data-pack)))
              (setq *tsp-scale-section* (nth 13 data-pack))
              (setq *tsp-scale-plan* (nth 14 data-pack))
              
              ;; 기존 프로젝트와의 호환성을 위한 방어 로직 (배열 크기 확인) 및 도면 딕셔너리 동기화
              (if (> (length data-pack) 15)
                (progn
                  (setq *tsp-deleted-post-points* (nth 15 data-pack))
                  (setq *tsp-added-post-points* (nth 16 data-pack))
                  
                  ;; [좌표 보정 로직 추가] 
                  ;; 기존 경계선(old)과 현재 경계선(new) 간의 위치 이동량(Shift)을 계산하여 수동 편집 절대좌표들을 새 위치에 맞게 이동
                  (setq old-start-pt (cdr (assoc 'V-START (nth 0 saved-segments))))
                  (setq new-start-pt (cdr (assoc 'V-START (nth 0 *segment-list*))))
                  (if (and old-start-pt new-start-pt)
                    (progn
                      (setq delta-x (- (car new-start-pt) (car old-start-pt)))
                      (setq delta-y (- (cadr new-start-pt) (cadr old-start-pt)))
                      
                      ;; 1. 삭제된 말뚝(DELETED_POSTS) 좌표 보정
                      (setq translated-deleted '())
                      (if *tsp-deleted-post-points*
                        (foreach pt *tsp-deleted-post-points*
                          (setq translated-deleted (append translated-deleted (list (list (+ (car pt) delta-x) (+ (cadr pt) delta-y) 0.0))))
                        )
                      )
                      (setq *tsp-deleted-post-points* translated-deleted)
                      
                      ;; 2. 추가된 말뚝(ADDED_POSTS) 좌표 보정
                      (setq translated-added '())
                      (if *tsp-added-post-points*
                        (foreach rec *tsp-added-post-points*
                          (setq pt (car rec))
                          (setq new-pt (list (+ (car pt) delta-x) (+ (cadr pt) delta-y) 0.0))
                          (setq translated-added (append translated-added (list (cons new-pt (cdr rec)))))
                        )
                      )
                      (setq *tsp-added-post-points* translated-added)

                      ;; 3. 버팀보 수동 지정 절대좌표(manual-pts) 보정 (*tsp-support-list* 갱신) 및 디버그
                      (princ (strcat "\n[디버그] 계산된 이동량 -> delta-x: " (rtos delta-x 2 4) ", delta-y: " (rtos delta-y 2 4)))
                      (setq translated-support '())
                      (if *tsp-support-list*
                        (foreach sup *tsp-support-list*
                          (setq shifted-sup '())
                          (setq j 0)
                          ;; 내부 루프: 지원 리스트(sup) 내의 각 항목(item)을 검사하며 좌표 보정
                            (foreach item sup
                              (if (= j 8)
                                (if item
 
                                  (if (listp item)
                                    (progn
                                      (princ "\n[디버그] 원본 manual-pts(리스트): ") (princ item)
                                      (setq shifted-item (mapcar (function (lambda (pt) (list (+ (car pt) delta-x) (+ (cadr pt) delta-y) (if (caddr pt) (caddr pt) 0.0)))) item))
                                      (princ "\n[디버그] 보정된 manual-pts: ") (princ shifted-item)
                                      (setq shifted-sup (append shifted-sup (list shifted-item)))
                                    )
                                    (progn
                                      (princ "\n[디버그] 원본 manual-pts(문자열/단일값 바이패스): ") (princ item)
                                      (setq shifted-sup (append shifted-sup (list item)))
                                    )
                                  )
                                  (setq shifted-sup (append shifted-sup (list nil)))
                                )
                                (setq shifted-sup (append shifted-sup (list item)))
                              )
                              (setq j (1+ j))
                            )
                          (setq translated-support (append translated-support (list shifted-sup)))
                        )
                      )
                      (setq *tsp-support-list* translated-support)

                      ;; 4. *segment-list* 내의 SUPPORT-LIST에도 동일하게 보정된 좌표 갱신
                      ;; 설명: 전체 세그먼트를 순회하며 내부 SUPPORT-LIST의 버팀보 좌표도 동기화합니다.
                      (setq updated-segment-list '())
                      (if *segment-list*
                        (foreach seg *segment-list*
                          (setq sup-list (cdr (assoc 'SUPPORT-LIST seg)))
                          (if sup-list
                            (progn
                              (setq translated-seg-sup '())
                              (foreach sup sup-list
                                (setq shifted-sup '())
                                (setq j 0)
                                ;; 내부 루프: 세그먼트 내 지원 리스트(sup)의 각 항목(item)을 검사하며 좌표 보정
                                (foreach item sup
                                  (if (= j 8)
                                    (if item
                                      (if (listp item)
                                        (setq shifted-sup (append shifted-sup (list (mapcar (function (lambda (pt) (list (+ (car pt) delta-x) (+ (cadr pt) delta-y) (if (caddr pt) (caddr pt) 0.0)))) item))))
                                        (setq shifted-sup (append shifted-sup (list item)))
                                      )
                                      (setq shifted-sup (append shifted-sup (list nil)))
                                    )
                                    (setq shifted-sup (append shifted-sup (list item)))
                                  )
                                  (setq j (1+ j))
                                )
                                (setq translated-seg-sup (append translated-seg-sup (list shifted-sup)))
                              )
                              ;; subst를 통해 기존 세그먼트의 SUPPORT-LIST 데이터를 안전하게 갱신합니다.
                              (setq new-seg (subst (cons 'SUPPORT-LIST translated-seg-sup) (assoc 'SUPPORT-LIST seg) seg))
                              (setq updated-segment-list (append updated-segment-list (list new-seg)))
                            )
                            (setq updated-segment-list (append updated-segment-list (list seg)))
                          )
                        )
                      )
                      (setq *segment-list* updated-segment-list)
                    )
                  )

                  ;; 보정된 데이터를 현재 도면의 TSP_DICT에 물리적으로 기록하여 유실 방지
                  (vlax-ldata-put "TSP_DICT" "DELETED_POSTS" *tsp-deleted-post-points*)
                  (vlax-ldata-put "TSP_DICT" "ADDED_POSTS" *tsp-added-post-points*)
                )
                (progn
                  (setq *tsp-deleted-post-points* '())
                  (setq *tsp-added-post-points* '())
                  (vlax-ldata-put "TSP_DICT" "DELETED_POSTS" '())
                  (vlax-ldata-put "TSP_DICT" "ADDED_POSTS" '())
                )
              )
              
              (setq *tsp-current-project-name* proj-name)
              (princ (strcat "\n[시스템] 프로젝트 '" proj-name "' 의 설정값 업로드 완료."))
              T
            )
          )
        )
      )
    )
    (progn (alert "데이터를 불러올 수 없습니다.") nil)
  )
)


;;;;==========================================================================
;;;; defun tsp-delete-project-data : 데이터 딕셔너리에서 프로젝트 삭제
;;;;==========================================================================
(defun tsp-delete-project-data (proj-name / dict-name)
  (setq dict-name "TSP_DATA_DICT")
  (vlax-ldata-delete dict-name proj-name)
  (princ (strcat "\n[시스템] 프로젝트 '" proj-name "' 이(가) 삭제되었습니다."))
  T
)


;;;;==========================================================================
;;;; defun save-prompt-dialog-callback : 저장 버튼 클릭 시 팝업창 띄우기 (예:1, 아니오:2, 취소:0 반환)
;;;;==========================================================================
(defun save-prompt-dialog-callback (dcl-path / dcl-id result)
  (setq dcl-id (load_dialog dcl-path))
  (if (new_dialog "tsp_save_prompt" dcl-id)
    (progn
      (action_tile "btn_yes" "(done_dialog 1)")  ;; 다른 이름으로 저장
      (action_tile "btn_no" "(done_dialog 2)")   ;; 덮어쓰기
      (action_tile "cancel" "(done_dialog 0)")   ;; 취소
      (setq result (start_dialog))
      (unload_dialog dcl-id)
      result
    )
    0
  )
)


;;; ==========================================================================
;;; [SECTION 2-1] 그룹 및 객체 관리 유틸리티 (Group & Entity Utils)
;;; ==========================================================================


;;;;==========================================================================
;;;; defun tsp-get-entity-handle : 엔티티 고유 핸들(Handle) ID를 추출
;;;;==========================================================================
(defun tsp-get-entity-handle (ent)
  (cdr (assoc 5 (entget ent)))
)


;;;;==========================================================================
;;;; defun tsp-get-intersection-point : 두 직선(무한)의 교차점을 계산
;;;;==========================================================================
(defun tsp-get-intersection-point (p1 p2 p3 p4)
  ;; nil 옵션은 선분이 아닌 무한 직선으로 간주하여 교차점을 찾음을 의미
  (inters p1 p2 p3 p4 nil)
)

;;;;==========================================================================
;;;; defun tsp-clear-drawing-group : 특정 경계선에 종속된 기존 작도 그룹을 찾아 안전하게 삭제 및 분해하는 함수
;;;;==========================================================================
(defun tsp-clear-drawing-group (boundary-ent / handle group-name dict group pair ent-to-del ent-list debug-grp-del)
  ;; 1. 경계선 핸들을 기반으로 그룹명 생성
  (setq handle (tsp-get-entity-handle boundary-ent))
  (setq group-name (strcat "TSP_GRP_" handle))
  ;; 2. ACAD_GROUP 딕셔너리 검색
  (setq dict (dictsearch (namedobjdict) "ACAD_GROUP"))
  ;; 3. 해당 그룹이 존재할 경우 삭제 절차 진행
  (if (and dict (dictsearch (cdr (assoc -1 dict)) group-name))
    (progn
      (setq group (dictsearch (cdr (assoc -1 dict)) group-name))
      (princ (strcat "\n[시스템] 기존 객체 그룹 '" group-name "' 물리적 삭제 준비 중..."))
      
      (setq ent-list '())
      ;; STEP 1: 그룹 내에서 삭제할 엔티티 리스트만 먼저 수집 (루프 중 삭제 절대 금지)
      (foreach pair group
        (if (= (car pair) 340)
          (setq ent-list (cons (cdr pair) ent-list))
        )
      )
      
      ;; STEP 2: 그룹 정의를 딕셔너리에서 먼저 제거하여 캐드 내부의 메모리 종속성 완전 파괴
      (dictremove (cdr (assoc -1 dict)) group-name)
      (princ "\n[시스템] 그룹 종속성 해제 완료. 개별 객체 삭제 시작...")
      
      ;; STEP 3: 종속성이 끊어진 상태에서 안전하게 물리적 삭제 (entdel) 진행
      (setq debug-grp-del 0)
      (foreach ent-to-del ent-list
        (if (entget ent-to-del)
          (progn
            ;; vl-catch-all-apply로 감싸 만에 하나 발생할 수 있는 에러 스킵
            (vl-catch-all-apply 'entdel (list ent-to-del))
            (setq debug-grp-del (1+ debug-grp-del))
          )
        )
      )
      (princ (strcat "\n[디버그: TSP] 메모리 충돌 없이 안전하게 물리적 삭제된 객체 수: " (itoa debug-grp-del)))
    )
    (princ (strcat "\n[디버그: TSP] 삭제할 그룹 '" group-name "'을 ACAD_GROUP에서 찾을 수 없습니다."))
  )
)


;;;;==========================================================================
;;;; defun tsp-group-last-entities : 생성된 객체고유 그룹화
;;;;==========================================================================
(defun tsp-group-last-entities (start-ent boundary-ent / sset ent handle group-name debug-ss-cnt dict acad-obj doc groups new-group valid-objs i obj-array)
  (setq handle (tsp-get-entity-handle boundary-ent))
  (setq group-name (strcat "TSP_GRP_" handle))
  
  (princ "\n[DEBUG-GROUP] 01. 선택 세트 생성 직전")
  (setq sset (ssadd))
  
  (if start-ent
    (progn
      (princ (strcat "\n[DEBUG-GROUP] 02. start-ent 확인. 타입: " (vl-princ-to-string (type start-ent))))
      
      ;; 크래시 유발 원인 확인: 객체가 지워졌는지 체크
      (if (entget start-ent)
        (princ "\n[DEBUG-GROUP] 03. start-ent가 도면에 유효하게 살아있음.")
        (princ "\n[DEBUG-GROUP] 03. 경고!!! start-ent가 방금 전 삭제 로직에 의해 파괴됨! (크래시 주원인)")
      )
      
      (princ "\n[디버그: TSP] 그룹화 시작점 (start-ent) 유효. 추적 시작...")
      
      (princ "\n[DEBUG-GROUP] 04. entnext 실행 직전 (여기서 죽으면 오토캐드 엔진 버그)")
      ;; 안전하게 다음 객체 탐색 시도
      (setq ent (vl-catch-all-apply 'entnext (list start-ent)))
      (if (vl-catch-all-error-p ent)
        (progn 
          (princ "\n[DEBUG-GROUP] 05-에러. entnext에서 메모리 참조 오류 발생 차단됨!") 
          (setq ent nil)
        )
        (princ "\n[DEBUG-GROUP] 05. entnext 통과 완료")
      )
    )
    (progn
      (princ "\n[디버그: TSP] 경고! 그룹화 시작점 (start-ent)이 nil입니다. 도면 처음부터 추적합니다.")
      (setq ent (entnext))
    )
  )
  
  (princ "\n[DEBUG-GROUP] 06. 객체 수집 While 루프 진입")
  (setq debug-ss-cnt 0)
  
  (while ent
    (if (= (rem debug-ss-cnt 1000) 0) 
      (princ (strcat "\n[DEBUG-GROUP] 루프 진행 중... 현재 추가된 객체 수: " (itoa debug-ss-cnt)))
    )
    
    (if (not (entget ent))
      (princ (strcat "\n[DEBUG-GROUP] 경고! 삭제된 불량 객체 감지됨. 인덱스: " (itoa debug-ss-cnt)))
      (vl-catch-all-apply 'ssadd (list ent sset))
    )
    
    (setq ent (vl-catch-all-apply 'entnext (list ent)))
    (if (vl-catch-all-error-p ent)
      (progn 
        (princ "\n[DEBUG-GROUP] 루프 탐색 중 다음 객체 포인터 에러 발생!") 
        (setq ent nil)
      )
    )
    (setq debug-ss-cnt (1+ debug-ss-cnt))
  )
  
  (princ (strcat "\n[디버그: TSP] 새로운 그룹화를 위해 수집된 엔티티 수: " (itoa debug-ss-cnt)))
  
  (if (> (sslength sset) 0)
    (progn
      (princ "\n[DEBUG-GROUP] 07. 그룹 딕셔너리 정리 및 ActiveX 그룹 생성 시작")
      
      ;; 1. ActiveX COM 객체 환경 초기화
      (setq acad-obj (vlax-get-acad-object))
      (setq doc (vla-get-activedocument acad-obj))
      (setq groups (vla-get-groups doc))
      
      ;; 2. 기존 그룹이 존재하면 삭제 (에러 무시)
      (vl-catch-all-apply 'vla-delete (list (vl-catch-all-apply 'vla-item (list groups group-name))))
      
      ;; 사전에서 한 번 더 찌꺼기 제거 (이중 안전장치)
      (setq dict (dictsearch (namedobjdict) "ACAD_GROUP"))
      (if (and dict (dictsearch (cdr (assoc -1 dict)) group-name))
        (dictremove (cdr (assoc -1 dict)) group-name)
      )
      
      (princ "\n[DEBUG-GROUP] 08. ActiveX 기반 새 그룹 생성 직전 (명령어 충돌 차단)")
      ;; 3. 명령어(vl-cmdf) 대신 데이터베이스(ActiveX)에 직접 그룹 생성
      (setq new-group (vl-catch-all-apply 'vla-add (list groups group-name)))
      
      (if (not (vl-catch-all-error-p new-group))
        (progn
          (vl-catch-all-apply 'vla-put-description (list new-group "TSP Auto-Gen"))
          
          ;; 4. 선택 세트(sset)에서 유효한 객체만 추출하여 배열로 변환 준비
          (setq valid-objs '())
          (setq i 0)
          (while (< i (sslength sset))
            (setq ent (ssname sset i))
            (if (entget ent)
              (setq valid-objs (cons (vlax-ename->vla-object ent) valid-objs))
            )
            (setq i (1+ i))
          )
          
          ;; 5. 안전 배열(SafeArray)로 묶어 그룹에 일괄 추가
          (if (> (length valid-objs) 0)
            (progn
              (setq valid-objs (reverse valid-objs))
              (setq obj-array (vlax-make-safearray vlax-vbobject (cons 0 (1- (length valid-objs)))))
              (setq i 0)
              (foreach obj valid-objs
                (vlax-safearray-put-element obj-array i obj)
                (setq i (1+ i))
              )
              (vl-catch-all-apply 'vla-appenditems (list new-group obj-array))
            )
          )
          (princ "\n[DEBUG-GROUP] 09. ActiveX 그룹 생성 및 객체 추가 완료")
          (princ (strcat "\n[시스템] " (itoa (length valid-objs)) "개의 객체가 '" group-name "' 그룹으로 안전하게 생성되었습니다."))
        )
        (princ "\n[경고] 그룹 생성 중 ActiveX 에러가 발생했습니다.")
      )
    )
    (princ "\n[경고] 생성된 객체가 없습니다.")
  )
  (princ "\n[DEBUG-GROUP] 10. 함수 종료 및 복귀")
)


;;;;==========================================================================
;;;; defun tsp-get-rock-start-depth : 지층 데이터에서 숏크리트 적용 암반선의 심도를 탐색하여 반환 (단위: m)
;;;;==========================================================================
(defun tsp-get-rock-start-depth ( / rock-depth found-rock prev-depth l-name l-depth l-type)
  (setq rock-depth nil) 
  (setq found-rock nil) 
  (setq prev-depth 0.0)
  (if (and *tsp-shotcrete-enable* (= *tsp-shotcrete-enable* "1") *tsp-soil-layers*)
    (foreach layer *tsp-soil-layers*
      (if (not found-rock)
        (progn
          (setq l-name (car layer)) 
          ;; 문자열과 숫자 모두 대응
          (setq l-depth (if (= (type (cadr layer)) 'STR) (atof (cadr layer)) (cadr layer)))
          (setq l-type (if (> (length layer) 5) (nth 5 layer) nil))
          
          (if (and *tsp-shotcrete-chk* (= *tsp-shotcrete-chk* "1") *tsp-shotcrete-layer* (/= *tsp-shotcrete-layer* ""))
            (if (= l-name *tsp-shotcrete-layer*)
              (progn (setq rock-depth prev-depth) (setq found-rock T))
            )
            (if (or (and l-type (or (wcmatch l-type "*풍화암*") (wcmatch l-type "*연암*") (wcmatch l-type "*경암*")))
                    (and l-name (or (wcmatch l-name "*풍화암*") (wcmatch l-name "*연암*") (wcmatch l-name "*경암*"))))
              (progn (setq rock-depth prev-depth) (setq found-rock T))
            )
          )
          (setq prev-depth l-depth)
        )
      )
    )
  )
  rock-depth ; 찾은 심도(m) 반환, 못 찾으면 nil 반환
)


;;; ==========================================================================
;;; [SECTION 3] 기하학 및 좌표 계산 (Geometry Utils)
;;; ==========================================================================


;;;;==========================================================================
;;;; defun extract-vertices : 엔티티(LWPOLYLINE 등)에서 정점 좌표(Vertex) 리스트 추출
;;;;==========================================================================
(defun extract-vertices (ent / ent-data vertices item elev pt-ocs pt-wcs first-pt last-pt)
  (setq ent-data (entget ent))
  (setq elev (cdr (assoc 38 ent-data)))
  (if (null elev) (setq elev 0.0))
  (setq vertices '())
  (foreach item ent-data
    (if (= (car item) 10)
      (progn
        ;; LWPOLYLINE의 DXF 10은 OCS 좌표이므로, 이를 WCS 절대좌표로 안전하게 변환
        (setq pt-ocs (list (nth 1 item) (nth 2 item) elev))
        (setq pt-wcs (trans pt-ocs ent 0))
        ;; Z축을 0으로 평탄화하여 2D 평면 연산 시 오차 및 안팎 뒤집힘 완벽 방지
        ;; [Phase 1] O(N) 최적화: cons로 앞에 붙임
        (setq vertices (cons (list (car pt-wcs) (cadr pt-wcs) 0.0) vertices))
      )
    )
  )
  ;; [Phase 1] 리스트를 원래 순서로 뒤집기
  (setq vertices (reverse vertices))
  
  ;; 폐합 여부 확인 후 중복 정점 제거
  (if (and (> (length vertices) 1)
           (setq first-pt (car vertices))
           (setq last-pt (last vertices))
           (equal first-pt last-pt 0.01))
    (setq vertices (reverse (cdr (reverse vertices))))
  )
  vertices
)


;;;;==========================================================================
;;;; defun get-polygon-orientation : 폴리곤의 방향(CW/CCW) 판별 (1: CCW, -1: CW)
;;;;==========================================================================
(defun get-polygon-orientation (vertices / signed-area i n x1 y1 x2 y2)
  (setq signed-area 0.0)
  (setq n (length vertices))
  (setq i 0)
  (while (< i n)
    (setq x1 (car (nth i vertices)))
    (setq y1 (cadr (nth i vertices)))
    (setq x2 (car (nth (if (= i (1- n)) 0 (1+ i)) vertices)))
    (setq y2 (cadr (nth (if (= i (1- n)) 0 (1+ i)) vertices)))
    (setq signed-area (+ signed-area (* (- x1 x2) (+ y1 y2))))
    (setq i (1+ i))
  )
  (if (> signed-area 0) 1 -1)
)


;;;;==========================================================================
;;;; defun is-closed-polyline : 폴리라인이 폐합되었는지 확인 (Flag 70 또는 시작점=끝점)
;;;;==========================================================================
(defun is-closed-polyline (ent / ent-data closed-flag vertices first-pt last-pt)
  (setq ent-data (entget ent))
  (setq closed-flag (cdr (assoc 70 ent-data)))
  (if (and closed-flag (= 1 (logand 1 closed-flag)))
    T
    (progn
      (setq vertices '())
      (foreach item ent-data
        (if (= (car item) 10) (setq vertices (append vertices (list (cdr item)))))
      )
      (if (>= (length vertices) 2)
        (equal (car vertices) (last vertices) 0.1)
        nil
      )
    )
  )
)


;;;;==========================================================================
;;;; defun is-corner-convex : 코너가 볼록한지 오목한지 판별 (외적 활용)
;;;;==========================================================================
(defun is-corner-convex (prev-pt curr-pt next-pt orientation / v1x v1y v2x v2y cross-product)
  (setq v1x (- (car curr-pt) (car prev-pt)))
  (setq v1y (- (cadr curr-pt) (cadr prev-pt)))
  (setq v2x (- (car next-pt) (car curr-pt)))
  (setq v2y (- (cadr next-pt) (cadr curr-pt)))
  (setq cross-product (- (* v1x v2y) (* v1y v2x)))
  (if (= orientation 1)
    (> cross-product 0)
    (< cross-product 0)
  )
)


;;;;==========================================================================
;;;; defun get-dist-point-to-segment : 점과 선분 사이의 최단 거리 계산
;;;;==========================================================================
(defun get-dist-point-to-segment (pt p1 p2 / x0 y0 x1 y1 x2 y2 dx dy t-param closest-x closest-y)
  (setq x0 (car pt) y0 (cadr pt))
  (setq x1 (car p1) y1 (cadr p1))
  (setq x2 (car p2) y2 (cadr p2))
  (setq dx (- x2 x1) dy (- y2 y1))
  (if (and (= dx 0) (= dy 0))
    (distance pt p1)
    (progn
      ;; 투영 계수 t 계산 (내적 활용)
      (setq t-param (/ (+ (* (- x0 x1) dx) (* (- y0 y1) dy)) (+ (* dx dx) (* dy dy))))
      ;; 선분 범위 내로 클램핑 (0 <= t <= 1)
      (if (< t-param 0) (setq t-param 0))
      (if (> t-param 1) (setq t-param 1))
      ;; 가장 가까운 점 좌표
      (setq closest-x (+ x1 (* t-param dx)))
      (setq closest-y (+ y1 (* t-param dy)))
      (distance pt (list closest-x closest-y))
    )
  )
)


;;;;==========================================================================
;;;; defun calc-orientation-by-closest-segment : 가상 연장선을 포함한 최적 방향 판별
;;;;==========================================================================
(defun calc-orientation-by-closest-segment (vertices user-pt / min-dist best-segment i p1 p2 p-prev p-next ext-len virt-start virt-end ext-segments dist cross-z)
  (setq ext-len 100000.0) ;; 충분히 긴 연장 길이
  ;; 1. 가상 연장점 생성
  (setq p1 (nth 0 vertices))
  (setq p2 (nth 1 vertices))
  (setq virt-start (polar p1 (angle p2 p1) ext-len)) ;; 시작점 뒤로 연장
  (setq p-prev (nth (- (length vertices) 2) vertices))
  (setq p-next (last vertices))
  (setq virt-end (polar p-next (angle p-prev p-next) ext-len)) ;; 끝점 앞으로 연장
  ;; 2. 전체 세그먼트 리스트 구성 (가상 시작 -> 본체 -> 가상 끝)
  (setq ext-segments (list (list virt-start (car vertices)))) ;; 가상 시작 세그먼트
  (setq i 0)
  (while (< i (1- (length vertices)))
    (setq ext-segments (append ext-segments (list (list (nth i vertices) (nth (1+ i) vertices)))))
    (setq i (1+ i))
  )
  (setq ext-segments (append ext-segments (list (list (last vertices) virt-end)))) ;; 가상 끝 세그먼트
  ;; 3. 가장 가까운 세그먼트 찾기
  (setq min-dist 1e99)
  (setq best-segment nil)
  (foreach seg ext-segments
    (setq dist (get-dist-point-to-segment user-pt (car seg) (cadr seg)))
    (if (< dist min-dist)
      (progn
        (setq min-dist dist)
        (setq best-segment seg)
      )
    )
  )
  ;; 4. 선택된 세그먼트 기준으로 외적(방향) 계산
  (if best-segment
    (progn
      (setq p1 (car best-segment))
      (setq p2 (cadr best-segment))
      (setq cross-z (- (* (- (car p2) (car p1)) (- (cadr user-pt) (cadr p1)))
                       (* (- (cadr p2) (cadr p1)) (- (car user-pt) (car p1)))))
      ;; 토류판(바깥쪽)과 띠장(안쪽)이 클릭한 방향에 맞게 정확히 생성되도록 부호 정상화
      (if (> cross-z 0) -1 1)
    )
    1 ;; 예외 시 기본값
  )
)


;;;;==========================================================================
;;;; defun determine-boundary-orientation : 경계선의 내부/외부 방향을 사용자 입력(가상 연장선 적용) 또는 자동 판별
;;;;==========================================================================
(defun determine-boundary-orientation (boundary-ent / vertices pt1 pt2 user-pt boundary-orient old-osmode)
  (princ "\n[방향 판별] 경계선 분석 중...")
  (setq vertices (extract-vertices boundary-ent))
  (if (is-closed-polyline boundary-ent)
    ;; [폐합된 경우] - 기존 로직 유지 (면적 부호로 판별)
    (progn
      (setq boundary-orient (get-polygon-orientation vertices))
      (princ (if (= boundary-orient 1) "\n- 폐합선: CCW (내부가 왼쪽)" "\n- 폐합선: CW (내부가 오른쪽)"))
      boundary-orient
    )
    (progn
      (setq old-osmode (getvar "OSMODE"))
      (setvar "OSMODE" 0)
      (princ "\n파일설치 위치(Outside) 선택 (객체스냅 임시해제) : ")
      (setq user-pt (getpoint))
      (setvar "OSMODE" old-osmode)
      (if user-pt
        (progn
          ;; 클릭한 UCS 좌표를 WCS 좌표로 변환 보정
          (setq user-pt (trans user-pt 1 0))
          ;; '연장선 분할' 논리 구현 함수 호출
          (setq boundary-orient (calc-orientation-by-closest-segment vertices user-pt))
          boundary-orient
        )
        (progn (princ "\n선택 취소됨.") nil)
      )
    )
  )
)


;;;;==========================================================================
;;;; defun calc-hpile-vertices : 중심점 기준으로 H-Pile 형상 점 좌표 계산 (12개 정점 + 4개 Fillet)
;;;;==========================================================================
(defun calc-hpile-vertices (center-pt h b tw tf / cx cy half-h half-b half-tw fillet-r)
  (setq cx (car center-pt))
  (setq cy (cadr center-pt))
  (setq half-h (/ h 2.0) half-b (/ b 2.0) half-tw (/ tw 2.0) fillet-r (* tw 2.0))
  (list
    (list (+ cx half-b) (+ cy half-h))                  ; pt1
    (list (+ cx half-b) (+ cy (- half-h tf)))           ; pt2
    (list (+ cx half-tw fillet-r) (+ cy (- half-h tf))) ; pt3a
    (list (+ cx half-tw) (+ cy (- half-h tf fillet-r))) ; pt3b
    (list (+ cx half-tw) (- cy (- half-h tf fillet-r))) ; pt9a
    (list (+ cx half-tw fillet-r) (- cy (- half-h tf))) ; pt9b
    (list (+ cx half-b) (- cy (- half-h tf)))           ; pt8
    (list (+ cx half-b) (- cy half-h))                  ; pt7
    (list (- cx half-b) (- cy half-h))                  ; pt12
    (list (- cx half-b) (- cy (- half-h tf)))           ; pt11
    (list (- cx half-tw fillet-r) (- cy (- half-h tf))) ; pt10a
    (list (- cx half-tw) (- cy (- half-h tf fillet-r))) ; pt10b
    (list (- cx half-tw) (+ cy (- half-h tf fillet-r))) ; pt4a
    (list (- cx half-tw fillet-r) (+ cy (- half-h tf))) ; pt4b
    (list (- cx half-b) (+ cy (- half-h tf)))           ; pt5
    (list (- cx half-b) (+ cy half-h))                  ; pt6
  )
)


;;;;==========================================================================
;;;; defun tsp-get-closest-vertex-index : 정점 리스트 재배열
;;;;==========================================================================
(defun tsp-get-closest-vertex-index (vertices pt / i min-dist best-idx dist p)
  (setq i 0 min-dist 1e99 best-idx 0)
  (foreach p vertices
    (setq dist (distance p pt))
    (if (< dist min-dist)
      (progn (setq min-dist dist) (setq best-idx i))
    )
    (setq i (1+ i))
  )
  best-idx
)


;;;;==========================================================================
;;;; defun tsp-shift-vertex-list : 자동 정리된 함수
;;;;==========================================================================
(defun tsp-shift-vertex-list (vertices idx / i len new-list)
  (setq len (length vertices))
  (setq new-list '())
  ;; 1. idx부터 끝까지 추가
  (setq i idx)
  (while (< i len)
    (setq new-list (append new-list (list (nth i vertices))))
    (setq i (1+ i))
  )
  ;; 2. 처음부터 idx 전까지 추가
  (setq i 0)
  (while (< i idx)
    (setq new-list (append new-list (list (nth i vertices))))
    (setq i (1+ i))
  )
  new-list
)
;;; ==========================================================================
;;; [SECTION 3-1] 세그먼트 데이터 초기화
;;; ==========================================================================


;;;;==========================================================================
;;;; defun init-segment-data : 상위에서 정렬된 vertices를 받아 세그먼트 초기화
;;;;==========================================================================
(defun init-segment-data (boundary-ent boundary-orient override-vertices / vertices is-closed num-segs i pt1 pt2 pt0 seg-angle seg-len seg-data new-list old-data use-existing is-convex default-brace-data ang-v1 ang-v2 diff prev-seg-len min-len old-brace-entry old-brace-val old-upg-entry old-first-seg old-pt1 new-pt1 delta-x delta-y translated-deleted translated-added translated-support j shifted-sup translated-seg-sup sup-list new-seg updated-segment-list pt new-pt rec sup item)
  (if (not (boundp '*segment-list*)) (setq *segment-list* nil))
  (if override-vertices
    (setq vertices override-vertices)
    (setq vertices (extract-vertices boundary-ent))
  )
  (setq is-closed (is-closed-polyline boundary-ent))
  (setq num-segs (if is-closed (length vertices) (1- (length vertices))))
  (setq use-existing nil)
  (if (and *segment-list* (= (length *segment-list*) num-segs))
    (setq use-existing T)
  )
  (if use-existing
    (progn
      (princ "\n[알림] 이전 작업 데이터를 불러옵니다.")
      
      ;; [도면 내 객체 복사/이동 시 좌표 보정 로직]
      (setq old-first-seg (nth 0 *segment-list*))
      (setq old-pt1 (cdr (assoc 'V-START old-first-seg)))
      (setq new-pt1 (nth 0 vertices))
      (setq delta-x (- (car new-pt1) (car old-pt1)))
      (setq delta-y (- (cadr new-pt1) (cadr old-pt1)))
      
      ;; 0.1 이상의 이동이 발생했을 경우에만 보정 실행
      (if (or (> (abs delta-x) 0.1) (> (abs delta-y) 0.1))
        (progn
          (princ (strcat "\n[시스템] 경계선 이동 감지 (dx: " (rtos delta-x 2 2) ", dy: " (rtos delta-y 2 2) "). 수동 말뚝 및 버팀보 좌표를 동기화합니다."))
          
          ;; 1. 삭제된 말뚝 보정
          (if (and (boundp '*tsp-deleted-post-points*) *tsp-deleted-post-points*)
            (progn
              (setq translated-deleted '())
              (foreach pt *tsp-deleted-post-points*
                (setq translated-deleted (cons (list (+ (car pt) delta-x) (+ (cadr pt) delta-y) 0.0) translated-deleted))
              )
              (setq *tsp-deleted-post-points* (reverse translated-deleted))
            )
          )
          
          ;; 2. 추가된 말뚝 보정
          (if (and (boundp '*tsp-added-post-points*) *tsp-added-post-points*)
            (progn
              (setq translated-added '())
              (foreach rec *tsp-added-post-points*
                (setq pt (car rec))
                (setq new-pt (list (+ (car pt) delta-x) (+ (cadr pt) delta-y) 0.0))
                (setq translated-added (cons (cons new-pt (cdr rec)) translated-added))
              )
              (setq *tsp-added-post-points* (reverse translated-added))
            )
          )
          
          ;; 3. 글로벌 버팀보 좌표 보정 (*tsp-support-list*) - 타입 검사(listp) 추가
          (if (and (boundp '*tsp-support-list*) *tsp-support-list*)
            (progn
              (setq translated-support '())
              (foreach sup *tsp-support-list*
                (setq shifted-sup '())
                (setq j 0)
                (foreach item sup
                  (if (= j 8)
                    (if (and item (listp item)) ; item이 리스트(좌표 배열)일 때만 mapcar 실행
                      (setq shifted-sup (cons (mapcar (function (lambda (pt) 
                                                                        (if (listp pt) ; pt도 정상적인 좌표 리스트인지 검증
                                                                          (list (+ (car pt) delta-x) (+ (cadr pt) delta-y) (if (caddr pt) (caddr pt) 0.0))
                                                                          pt
                                                                        )
                                                                      )) item) shifted-sup))
                      (setq shifted-sup (cons item shifted-sup)) ; 문자열이면 원본 유지
                    )
                    (setq shifted-sup (cons item shifted-sup))
                  )
                  (setq j (1+ j))
                )
                (setq translated-support (cons (reverse shifted-sup) translated-support))
              )
              (setq *tsp-support-list* (reverse translated-support))
            )
          )
          
          ;; 4. 세그먼트 내부 SUPPORT-LIST 보정 (*segment-list*) - 타입 검사(listp) 추가
          (setq updated-segment-list '())
          (foreach seg *segment-list*
            (setq sup-list (cdr (assoc 'SUPPORT-LIST seg)))
            (if sup-list
              (progn
                (setq translated-seg-sup '())
                (foreach sup sup-list
                  (setq shifted-sup '())
                  (setq j 0)
                  (foreach item sup
                    (if (= j 8)
                      (if (and item (listp item))
                        (setq shifted-sup (cons (mapcar (function (lambda (pt) 
                                                                        (if (listp pt)
                                                                          (list (+ (car pt) delta-x) (+ (cadr pt) delta-y) (if (caddr pt) (caddr pt) 0.0))
                                                                          pt
                                                                        )
                                                                      )) item) shifted-sup))
                        (setq shifted-sup (cons item shifted-sup))
                      )
                      (setq shifted-sup (cons item shifted-sup))
                    )
                    (setq j (1+ j))
                  )
                  (setq translated-seg-sup (cons (reverse shifted-sup) translated-seg-sup))
                )
                (setq new-seg (subst (cons 'SUPPORT-LIST (reverse translated-seg-sup)) (assoc 'SUPPORT-LIST seg) seg))
                (setq updated-segment-list (cons new-seg updated-segment-list))
              )
              (setq updated-segment-list (cons seg updated-segment-list))
            )
          )
          (setq *segment-list* (reverse updated-segment-list))
        )
      )
    )
    (princ (strcat "\n[STEP 1] " (itoa num-segs) "개의 세그먼트 데이터 초기화 중..."))
  )
  
  (setq new-list '())
  (setq i 0)
  (while (< i num-segs)
    (setq pt1 (nth i vertices))
    (setq pt2 (nth (if is-closed (rem (+ i 1) num-segs) (+ i 1)) vertices))
    (setq pt0 (if is-closed
                (nth (if (= i 0) (1- num-segs) (1- i)) vertices)
                (if (> i 0) (nth (1- i) vertices) nil)))
    (setq is-convex nil)
    (if (and pt0 pt2)
      (progn
        (if (is-corner-convex pt0 pt1 pt2 boundary-orient) (setq is-convex T))
        (setq ang-v1 (angle pt1 pt0))
        (setq ang-v2 (angle pt1 pt2))
        (setq diff (abs (- ang-v1 ang-v2)))
        (if (> diff pi) (setq diff (- (* 2.0 pi) diff)))
        (if (>= diff (* 160.0 (/ pi 180.0)))
          (setq is-convex nil)
        )
      )
    )
    (setq seg-len (distance pt1 pt2))
    (setq seg-angle (angle pt1 pt2))
    (setq prev-seg-len (if pt0 (distance pt0 pt1) seg-len))
    (setq min-len (min seg-len prev-seg-len))
    (if (< min-len 1000.0)
      (setq is-convex nil)
    )
    (setq default-brace-data
      (if is-convex
        (list "Y" nil "1" "0" "0.0" "1" "50")
        (list "N" nil)
      )
    )
    (if use-existing
      (progn
        (setq old-data (nth i *segment-list*))
        (setq seg-data (subst (cons 'V-START pt1) (assoc 'V-START old-data) old-data))
        (setq seg-data (subst (cons 'V-END pt2) (assoc 'V-END seg-data) seg-data))
        (setq seg-data (subst (cons 'ANGLE seg-angle) (assoc 'ANGLE seg-data) seg-data))
        (setq seg-data (subst (cons 'LENGTH seg-len) (assoc 'LENGTH seg-data) seg-data))
        (setq seg-data (subst (cons 'ID (1+ i)) (assoc 'ID seg-data) seg-data))
        (setq old-brace-entry (assoc 'CORNER-BRACE seg-data))
        (if old-brace-entry
          (progn
            (setq old-brace-val (cdr old-brace-entry))
            (if is-convex
              (if (= (car old-brace-val) "N")
                (setq seg-data (subst (cons 'CORNER-BRACE default-brace-data) old-brace-entry seg-data))
              )
              (setq seg-data (subst (cons 'CORNER-BRACE default-brace-data) old-brace-entry seg-data))
            )
          )
          (setq seg-data (append seg-data (list (cons 'CORNER-BRACE default-brace-data))))
        )
        (setq old-upg-entry (assoc 'UPGRADE-WALE seg-data))
        (if (not old-upg-entry)
          (setq seg-data (append seg-data (list (cons 'UPGRADE-WALE nil))))
        )
        (if (not (assoc 'WALL-TYPE seg-data))
          (setq seg-data (append seg-data (list (cons 'WALL-TYPE "HPILE"))))
        )
        (if (not (assoc 'CIP-MAX-DEPTH seg-data))
          (setq seg-data (append seg-data (list (cons 'CIP-MAX-DEPTH "10.0"))))
        )
        (if (not (assoc 'CIP-EMBED-DEPTH seg-data))
          (setq seg-data (append seg-data (list (cons 'CIP-EMBED-DEPTH "3.0"))))
        )
        (if (not (assoc 'CIP-HPILE-IDX seg-data))
          (setq seg-data (append seg-data (list (cons 'CIP-HPILE-IDX "2"))))
        )
        (if (not (assoc 'CIP-WALE-IDX seg-data))
          (setq seg-data (append seg-data (list (cons 'CIP-WALE-IDX "2"))))
        )
        (if (not (assoc 'CIP-DIA seg-data))
          (setq seg-data (append seg-data (list (cons 'CIP-DIA "500"))))
        )
        (if (not (assoc 'CIP-MODE-IDX seg-data))
          (setq seg-data (append seg-data (list (cons 'CIP-MODE-IDX "0"))))
        )
        (if (not (assoc 'CIP-OVERLAP seg-data))
          (setq seg-data (append seg-data (list (cons 'CIP-OVERLAP "0"))))
        )
        (if (not (assoc 'CIP-EQUAL-DIVIDE seg-data))
          (setq seg-data (append seg-data (list (cons 'CIP-EQUAL-DIVIDE "0"))))
        )
        (if (not (assoc 'CIP-INTERVAL-IDX seg-data))
          (setq seg-data (append seg-data (list (cons 'CIP-INTERVAL-IDX "2"))))
        )
        (if (not (assoc 'CIP-GROUTING-IDX seg-data))
          (setq seg-data (append seg-data (list (cons 'CIP-GROUTING-IDX "0"))))
        )
      )
      (progn
        (setq seg-data (list
          (cons 'ID (1+ i))
          (cons 'NAME (strcat "Seg-" (itoa (1+ i))))
          (cons 'IS-DEFINED nil)
          (cons 'SECTION-DRAW nil)
          (cons 'SOIL-DATA nil)
          (cons 'WALL-SPEC *tsp-hpile-spec*)
          (cons 'WALL-CUSTOM '(300 300 10 15))
          (cons 'WALE-SPEC *tsp-wale-spec*)
          (cons 'WALE-CUSTOM '(300 300 10 15))
          (cons 'CTC 2.0)
          (cons 'TIMBER-THICKNESS 60)
          (cons 'MAX-DEPTH 10.0)
          (cons 'EMBED-DEPTH 3.0)
          (cons 'WATER-CHK "0")
          (cons 'WATER-DEPTH 0.0)
          (cons 'SHOTCRETE-ENABLE "1")
          (cons 'SHOTCRETE-CHK "0")
          (cons 'SHOTCRETE-LAYER "")
          (cons 'SHOTCRETE-THICK 0.0)
          (cons 'SUPPORT-LIST '())
          (cons 'CORNER-BRACE default-brace-data)
          (cons 'UPGRADE-WALE nil)
          (cons 'WALL-TYPE "HPILE")
          (cons 'CIP-MAX-DEPTH "10.0")
          (cons 'CIP-EMBED-DEPTH "3.0")
          (cons 'CIP-HPILE-IDX "2")
          (cons 'CIP-WALE-IDX "2")
          (cons 'CIP-DIA "500")
          (cons 'CIP-MODE-IDX "0")
          (cons 'CIP-OVERLAP "0")
          (cons 'CIP-EQUAL-DIVIDE "0")
          (cons 'CIP-INTERVAL-IDX "2")
          (cons 'CIP-GROUTING-IDX "0")
          (cons 'V-START pt1)
          (cons 'V-END pt2)
          (cons 'ANGLE seg-angle)
          (cons 'LENGTH seg-len)
        ))
      )
    )
    ;; [Phase 1] cons 최적화
    (setq new-list (cons seg-data new-list))
    (setq i (1+ i))
  )
  (setq *segment-list* (reverse new-list))
  (princ "\n[완료] 세그먼트 리스트 준비됨.")
  (princ (strcat "\n - 총 세그먼트 수: " (itoa (length *segment-list*))))
)

;;; ==========================================================================
;;; [SECTION 4] 단면도 및 주상도 작도 (Section & Soil Profile)
;;; ==========================================================================


;;;;==========================================================================
;;;; defun create-wale-section-block : 단면 띠장(Wale) 블록 정의
;;;;==========================================================================
(defun create-wale-section-block (h b tw tf / block-name pts layer-name)
    ;; 블록 이름과 레이어 이름 생성
    (setq block-name (strcat "_WALE(" (itoa h) "x" (itoa b) "x" (itoa tw) "x" (itoa tf) ")"))
    (setq layer-name (strcat "_H-Pile_" (itoa h) "x" (itoa b) "x" (itoa tw) "-" (itoa tf)))
    (if (or (null layer-name) (= layer-name "")) (setq layer-name "0"))
    ;; 블록이 없으면 생성
    (if (not (tblsearch "BLOCK" block-name))
      (progn
        ;; 필요한 레이어 생성
        (create-layer-if-not-exists layer-name "3")
        (create-layer-if-not-exists "_띠장 point" "1")
        (create-layer-if-not-exists "_띠장(wale)" "3")
        (entmake (list '(0 . "BLOCK") (cons 2 block-name) '(70 . 0) '(10 . (0.0 0.0 0.0))))
        (setq pts (calc-hpile-vertices (list 0.0 (/ h 2.0) 0.0) h b tw tf))
        ;; 1. H-Pile 형상 작도
        (entmake (list '(0 . "LWPOLYLINE") '(100 . "AcDbEntity") '(100 . "AcDbPolyline")
          (cons 8 layer-name) (cons 62 256) '(90 . 20) '(70 . 1)
          (cons 10 (nth 0 pts))  (cons 10 (nth 1 pts))
          (cons 10 (nth 2 pts))  (cons 42 0.4142135623730951) (cons 10 (nth 3 pts))
          (cons 10 (nth 4 pts))  (cons 42 0.4142135623730951) (cons 10 (nth 5 pts))
          (cons 10 (nth 6 pts))  (cons 10 (nth 7 pts))
          (cons 10 (nth 8 pts))  (cons 10 (nth 9 pts))
          (cons 10 (nth 10 pts)) (cons 42 0.4142135623730951) (cons 10 (nth 11 pts))
          (cons 10 (nth 12 pts)) (cons 42 0.4142135623730951) (cons 10 (nth 13 pts))
          (cons 10 (nth 14 pts)) (cons 10 (nth 15 pts))))
        ;; 2. STIFFNER_외곽 모서리 직사각형 (pt1-pt7-pt12-pt6)
        (entmake (list '(0 . "LWPOLYLINE") '(100 . "AcDbEntity") '(100 . "AcDbPolyline")
          (cons 8 "_띠장(wale)") (cons 62 256) '(90 . 4) '(70 . 1)
          (cons 10 (nth 0 pts))   ;; pt1 (우상단)
          (cons 10 (nth 7 pts))   ;; pt7 (우하단)
          (cons 10 (nth 8 pts))   ;; pt12 (좌하단)
          (cons 10 (nth 15 pts))  ;; pt6 (좌상단)
        ))
        (entmake (list '(0 . "POINT") (cons 8 "_띠장 point") (cons 62 256) '(10 0.0 0.0 0.0)))
        (entmake (list '(0 . "ENDBLK")))
      )
    )
    block-name
  )


;;;;==========================================================================
;;;; defun draw-water-level-symbol : 지하수위 기호(삼각형 역상) 및 수위 텍스트 작도
;;;;==========================================================================
(defun draw-water-level-symbol (base-pt depth-val col-x-right / layer-name line1-mid line1-start line1-end line2-start line2-end line3-start line3-end tri-p1 tri-p2 tri-p3 text-pt text-str s-factor tri-h tri-w-half line1-len l2-half off-y1 line2-y l3-half off-y2 line3-y tri-p_top_center text-gap text-h)
  (setq layer-name "_지반선")
  (setq s-factor (/ *tsp-scale-section* 200.0))
  (setq tri-h (* 800.0 s-factor))
  (setq tri-w-half (/ tri-h (sqrt 3.0)))
  (setq line1-len (* 3000.0 s-factor))
  (setq line1-start (list col-x-right (cadr base-pt) 0.0))
  (setq line1-end (list (+ col-x-right line1-len) (cadr base-pt) 0.0))
  (setq line1-mid (list (/ (+ (car line1-start) (car line1-end)) 2.0) (cadr base-pt) 0.0))
  (entmake (list '(0 . "LWPOLYLINE") '(100 . "AcDbEntity") '(100 . "AcDbPolyline") (cons 8 layer-name) (cons 62 8) '(90 . 2) '(70 . 0) (cons 10 line1-start) (cons 10 line1-end)))
  (setq l2-half (* 750.0 s-factor)) (setq off-y1 (* 100.0 s-factor)) (setq line2-y (- (cadr line1-mid) off-y1))
  (setq line2-start (list (- (car line1-mid) l2-half) line2-y 0.0)) (setq line2-end (list (+ (car line1-mid) l2-half) line2-y 0.0))
  (entmake (list '(0 . "LWPOLYLINE") '(100 . "AcDbEntity") '(100 . "AcDbPolyline") (cons 8 layer-name) (cons 62 8) '(90 . 2) '(70 . 0) (cons 10 line2-start) (cons 10 line2-end)))
  (setq l3-half (* 500.0 s-factor)) (setq off-y2 (* 200.0 s-factor)) (setq line3-y (- (cadr line1-mid) off-y2))
  (setq line3-start (list (- (car line1-mid) l3-half) line3-y 0.0)) (setq line3-end (list (+ (car line1-mid) l3-half) line3-y 0.0))
  (entmake (list '(0 . "LWPOLYLINE") '(100 . "AcDbEntity") '(100 . "AcDbPolyline") (cons 8 layer-name) (cons 62 8) '(90 . 2) '(70 . 0) (cons 10 line3-start) (cons 10 line3-end)))
  (setq tri-p3 line1-mid)
  (setq tri-p1 (list (- (car line1-mid) tri-w-half) (+ (cadr line1-mid) tri-h) 0.0))
  (setq tri-p2 (list (+ (car line1-mid) tri-w-half) (+ (cadr line1-mid) tri-h) 0.0))
  (entmake (list '(0 . "LWPOLYLINE") '(100 . "AcDbEntity") '(100 . "AcDbPolyline") (cons 8 layer-name) (cons 62 8) '(90 . 3) '(70 . 1) (cons 10 tri-p1) (cons 10 tri-p2) (cons 10 tri-p3)))
  (setq tri-p_top_center (list (car line1-mid) (+ (cadr line1-mid) tri-h) 0.0))
  (entmake (list '(0 . "SOLID") '(100 . "AcDbEntity") '(100 . "AcDbTrace") (cons 8 layer-name) (cons 62 8) (cons 10 tri-p1) (cons 11 tri-p_top_center) (cons 12 tri-p3) (cons 13 tri-p3)))
  (setq text-gap (* 400.0 s-factor))
  (setq text-str (strcat "-" (format-depth-text depth-val) "m"))
  (setq text-pt (list (car line1-mid) (+ (cadr line1-mid) tri-h text-gap) 0.0))
  (setq text-h (* 600.0 s-factor))
  (entmake (list '(0 . "TEXT") '(100 . "AcDbEntity") '(100 . "AcDbText") (cons 8 layer-name) (cons 62 8) (cons 10 text-pt) (cons 40 text-h) (cons 1 text-str) (cons 72 1) (cons 11 text-pt)))
)


;;;;==========================================================================
;;;; defun draw-soil-column : 지반 주상도(Soil Column) 생성 및 지층별 해치/텍스트 표기
;;;;==========================================================================
(defun draw-soil-column (top-left-pt side / prev-depth curr-depth layer-name layer-depth layer-hatch layer-scale layer-angle col-width y-curr y-prev rect-pl start-x s-factor txt-h leader-len txt-off-l txt-off-c col-x-right pt1 pt2 pt3 pt4 wl-y wl-pt l-name l-depth l-pattern l-scale l-angle text-x text-y-name center-pt base-scale final-scale final-angle hole-text-x hole-text-y n-item n-depth n-str n-y n-pt1 n-pt2 n-text-pt)
  (setq layer-name "_지반선")
  (setq s-factor (/ *tsp-scale-section* 200.0))
  (setq col-width (* 1000.0 s-factor)) (setq txt-h (* 600.0 s-factor)) (setq leader-len (* 1000.0 s-factor)) (setq txt-off-l (* 1200.0 s-factor)) (setq txt-off-c (* 3500.0 s-factor))
  (setq prev-depth 0.0)
  (if (= side "L") (setq start-x (- (car top-left-pt) col-width)) (setq start-x (car top-left-pt)))
  (setq top-left-pt (list start-x (cadr top-left-pt) 0.0))
  (setq col-x-right (+ start-x col-width))
  (entmake (list '(0 . "LWPOLYLINE") '(100 . "AcDbEntity") '(100 . "AcDbPolyline") (cons 8 layer-name) (cons 62 8) '(90 . 2) '(70 . 0) (cons 10 (list (car top-left-pt) (cadr top-left-pt))) (cons 10 (list (- (car top-left-pt) leader-len) (cadr top-left-pt)))))
  (entmake (list '(0 . "TEXT") '(100 . "AcDbEntity") '(100 . "AcDbText") (cons 8 layer-name) (cons 62 8) (cons 10 (list (- (car top-left-pt) txt-off-l) (cadr top-left-pt) 0.0)) (cons 40 txt-h) (cons 1 (format-depth-text 0.0)) (cons 72 2) (cons 11 (list (- (car top-left-pt) txt-off-l) (cadr top-left-pt) 0.0))))
  (if (= *tsp-water-chk* "1")
    (progn
      (setq wl-y (- (cadr top-left-pt) (* *tsp-water-depth* 1000.0)))
      (setq wl-x (+ col-x-right (* 3000.0 s-factor)))
      (setq wl-pt (list wl-x wl-y 0.0))
      (draw-water-level-symbol wl-pt *tsp-water-depth* wl-x)
    )
  )
  (foreach layer *tsp-soil-layers*
    (setq l-name (car layer)) (setq l-depth (cadr layer)) (setq l-pattern (nth 2 layer)) (setq l-scale (nth 3 layer)) (setq l-angle (nth 4 layer))
    (setq curr-depth (* l-depth 1000.0)) (setq y-prev (- (cadr top-left-pt) prev-depth)) (setq y-curr (- (cadr top-left-pt) curr-depth))
    (setq pt1 (list (car top-left-pt) y-prev)) (setq pt2 (list (+ (car top-left-pt) col-width) y-prev)) (setq pt3 (list (+ (car top-left-pt) col-width) y-curr)) (setq pt4 (list (car top-left-pt) y-curr))
    (setq center-pt (list (/ (+ (car pt1) (car pt3)) 2.0) (/ (+ (cadr pt1) (cadr pt3)) 2.0) 0.0))
    (entmake (list '(0 . "LWPOLYLINE") '(100 . "AcDbEntity") '(100 . "AcDbPolyline") (cons 8 layer-name) (cons 62 8) '(90 . 4) '(70 . 1) (cons 10 pt1) (cons 10 pt2) (cons 10 pt3) (cons 10 pt4)))
    (setq rect-pl (entlast))
    ;; 배열에 저장된 l-scale과 l-angle 적용
    (setq base-scale (if (and l-scale (> l-scale 0)) l-scale 100.0))
    (setq final-scale (* base-scale (/ *tsp-scale-section* 200.0)))
    (setq final-angle (if l-angle l-angle 0.0))
    (if rect-pl
      (tsp-apply-custom-hatch rect-pl l-pattern final-scale (* final-angle (/ pi 180.0)) layer-name 8 center-pt)
    )
    (entmake (list '(0 . "LWPOLYLINE") '(100 . "AcDbEntity") '(100 . "AcDbPolyline") (cons 8 layer-name) (cons 62 8) '(90 . 2) '(70 . 0) (cons 10 pt4) (cons 10 (list (- (car pt4) leader-len) (cadr pt4)))))
    (entmake (list '(0 . "TEXT") '(100 . "AcDbEntity") '(100 . "AcDbText") (cons 8 layer-name) (cons 62 8) (cons 10 (list (- (car pt4) txt-off-l) (cadr pt4) 0.0)) (cons 40 txt-h) (cons 1 (format-depth-text l-depth)) (cons 72 2) (cons 11 (list (- (car pt4) txt-off-l) (cadr pt4) 0.0))))
    (setq text-x (- (+ (car pt1) (/ col-width 2.0)) txt-off-c))
    (setq text-y-name (- (/ (+ y-prev y-curr) 2.0) (/ txt-h 2.0)))
    (entmake (list '(0 . "TEXT") '(100 . "AcDbEntity") '(100 . "AcDbText") (cons 8 layer-name) (cons 62 8) (cons 10 (list text-x text-y-name 0.0)) (cons 40 txt-h) (cons 1 l-name) (cons 72 2) (cons 11 (list text-x text-y-name 0.0))))
    (setq prev-depth curr-depth)
  )
;;;;==========================================================================
;;;; N치 및 시추공 번호(HOLE No.) 우측 작도 로직
;;;;==========================================================================
  (if (and *tsp-hole-no* (/= *tsp-hole-no* ""))
    (progn
      (setq h-txt-h (* 500.0 s-factor))
      (setq center-top-x (+ start-x (/ col-width 2.0)))
      (setq center-top-y (cadr top-left-pt))
      (setq line-top-y (+ center-top-y (* 1000.0 s-factor)))

      ;; 1. 중심 수직선 (길이 1000)
      (entmake (list '(0 . "LWPOLYLINE") '(100 . "AcDbEntity") '(100 . "AcDbPolyline") (cons 8 layer-name) (cons 62 8) '(90 . 2) '(70 . 0) (cons 10 (list center-top-x center-top-y)) (cons 10 (list center-top-x line-top-y))))

      ;; 2. 직사각형 박스 (가로 2200, 세로 800)
      (setq box-hw (* 1100.0 s-factor))
      (setq box-h (* 800.0 s-factor))
      (setq p1 (list (- center-top-x box-hw) line-top-y))
      (setq p2 (list (+ center-top-x box-hw) line-top-y))
      (setq p3 (list (+ center-top-x box-hw) (+ line-top-y box-h)))
      (setq p4 (list (- center-top-x box-hw) (+ line-top-y box-h)))
      (entmake (list '(0 . "LWPOLYLINE") '(100 . "AcDbEntity") '(100 . "AcDbPolyline") (cons 8 layer-name) (cons 62 8) '(90 . 4) '(70 . 1) (cons 10 p1) (cons 10 p2) (cons 10 p3) (cons 10 p4)))

      ;; 3. 시추공 번호 텍스트 (박스 중앙 정렬)
      (setq text-y (+ line-top-y (* 400.0 s-factor)))
      (entmake (list '(0 . "TEXT") '(100 . "AcDbEntity") '(100 . "AcDbText") 
                     (cons 8 layer-name) (cons 62 8) 
                     (cons 10 (list center-top-x text-y 0.0)) 
                     (cons 40 h-txt-h)
                     (cons 1 *tsp-hole-no*) 
                     (cons 72 1) (cons 11 (list center-top-x text-y 0.0)) (cons 73 2)))
    )
  )
  
  (if *tsp-n-values*
    (progn
      (setq leader-len (* 2000.0 s-factor))
      (foreach n-item *tsp-n-values*
        (setq n-depth (* (car n-item) 1000.0))
        (setq n-str (cadr n-item))
        (setq n-y (- (cadr top-left-pt) n-depth))
        
        (setq n-pt1 (list col-x-right n-y))
        (setq n-pt2 (list (+ col-x-right leader-len) n-y))
        
        ;; 지시선 그리기
        (entmake (list '(0 . "LWPOLYLINE") '(100 . "AcDbEntity") '(100 . "AcDbPolyline") (cons 8 layer-name) (cons 62 8) '(90 . 2) '(70 . 0) (cons 10 n-pt1) (cons 10 n-pt2)))
        
        ;; N치 텍스트 (지시선 시작점 n-pt1에서 오른쪽으로 100만큼 여백을 두고 배치)
        (setq n-text-pt (list (+ (car n-pt1) (* 100.0 s-factor)) (+ n-y (* 150.0 s-factor)) 0.0))
        (entmake (list '(0 . "TEXT") '(100 . "AcDbEntity") '(100 . "AcDbText") 
                       (cons 8 layer-name) (cons 62 8) 
                       (cons 10 n-text-pt) 
                       (cons 40 txt-h) 
                       (cons 1 n-str)))
      )
    )
  )
  (princ "\n주상도 생성 완료.")
)


;;;;==========================================================================
;;;; defun draw-wale-section : 띠장 삽입 및 보걸이 상세 작도
;;;;==========================================================================
(defun draw-wale-section (insert-pt rotation layer-name w-h w-b w-tw w-tf extra-margin br-offset / block-name br-layer cx cy wale-dir y-base y-L1 y-L2 y-L3 x-wall x-tip x-L4-start pt-L1-s pt-L1-e pt-L2-s pt-L2-e pt-L3-s pt-L3-e pt-L4-s pt-L4-e pt-L5-s pt-L5-e pt-L6-s pt-L6-e pt-L7-s pt-L7-e k4 k6 k7 is-left trim-x-6 trim-x-7 intersect-x8)
  (setq block-name (create-wale-section-block w-h w-b w-tw w-tf))
  (entmake (list '(0 . "INSERT") (cons 2 block-name) (cons 8 layer-name) (cons 10 insert-pt) '(41 . 1.0) '(42 . 1.0) '(43 . 1.0) (cons 50 rotation)))
  (setq br-layer "_보걸이(Angle Bracket)")
  (create-layer-if-not-exists br-layer "7")
  (setq cx (car insert-pt) cy (cadr insert-pt))
  (if (< (sin rotation) -0.1) (setq wale-dir 1.0) (setq wale-dir -1.0))
  (setq is-left (> wale-dir 0))
  (setq y-base (- cy (/ w-b 2.0)))
  (setq y-L1 y-base)
  (setq y-L2 (- y-base 10.0))
  (setq y-L3 (- y-base 100.0))
  (setq x-wall (- cx (* (if br-offset br-offset 0.0) wale-dir)))
  (setq x-tip (+ cx (* (+ w-h extra-margin) wale-dir)))
  (setq pt-L1-s (list x-wall y-L1 0.0)) (setq pt-L1-e (list x-tip y-L1 0.0))
  (setq pt-L2-s (list x-wall y-L2 0.0)) (setq pt-L2-e (list x-tip y-L2 0.0))
  (setq pt-L3-s pt-L1-e) (setq pt-L3-e (list (car pt-L1-e) y-L3 0.0))
  (setq x-L4-start (- x-tip (* 30.0 wale-dir)))
  (setq pt-L4-s (list x-L4-start y-L2 0.0))
  (if is-left (setq k4 (- y-L2 x-L4-start)) (setq k4 (+ y-L2 x-L4-start)))
  (if is-left (setq pt-L4-e (list x-wall (+ x-wall k4) 0.0)) (setq pt-L4-e (list x-wall (- k4 x-wall) 0.0)))
  (setq pt-L5-s pt-L3-e)
  (if is-left (setq pt-L5-e (list (- y-L3 k4) y-L3 0.0)) (setq pt-L5-e (list (- k4 y-L3) y-L3 0.0)))
  (setq k6 (+ k4 (* 90.0 (sqrt 2.0))))
  (if is-left (setq trim-x-6 (- y-L2 k6)) (setq trim-x-6 (- k6 y-L2)))
  (setq pt-L6-s (list trim-x-6 y-L2 0.0)) (setq pt-L6-e (list x-wall (if is-left (+ x-wall k6) (- k6 x-wall)) 0.0))
  (setq k7 (+ k6 (* 10.0 (sqrt 2.0))))
  (if is-left (setq trim-x-7 (- y-L2 k7)) (setq trim-x-7 (- k7 y-L2)))
(setq pt-L7-s (list trim-x-7 y-L2 0.0)) (setq pt-L7-e (list x-wall (if is-left (+ x-wall k7) (- k7 x-wall)) 0.0))
  (foreach pts (list (list pt-L1-s pt-L1-e) (list pt-L3-s pt-L3-e) (list pt-L4-s pt-L4-e)
                     (list pt-L5-s pt-L5-e) (list pt-L7-s pt-L7-e))
    (entmake (list '(0 . "LWPOLYLINE") '(100 . "AcDbEntity") '(100 . "AcDbPolyline")
      (cons 8 br-layer) (cons 62 256) '(90 . 2) '(70 . 0) (cons 10 (car pts)) (cons 10 (cadr pts)))))
  (foreach pts (list (list pt-L2-s pt-L2-e) (list pt-L6-s pt-L6-e))
    (entmake (list '(0 . "LWPOLYLINE") '(100 . "AcDbEntity") '(100 . "AcDbPolyline")
      (cons 8 br-layer) (cons 62 1) '(90 . 2) '(70 . 0) (cons 10 (car pts)) (cons 10 (cadr pts)))))
)

;;;;==========================================================================
;;;; defun draw-vertical-hpile : H-Pile 수직 단면선 작도
;;;;==========================================================================
(defun draw-vertical-hpile (x-left x-right y-top y-bot tf layer-name / x-in-l x-in-r p-out-l-top p-out-l-bot p-in-l-top p-in-l-bot p-in-r-top p-in-r-bot p-out-r-top p-out-r-bot)
  (setq x-in-l (+ x-left tf))
  (setq x-in-r (- x-right tf))
  
  (setq p-out-l-top (list x-left y-top 0.0))
  (setq p-out-l-bot (list x-left y-bot 0.0))
  (setq p-in-l-top (list x-in-l y-top 0.0))
  (setq p-in-l-bot (list x-in-l y-bot 0.0))
  (setq p-in-r-top (list x-in-r y-top 0.0))
  (setq p-in-r-bot (list x-in-r y-bot 0.0))
  (setq p-out-r-top (list x-right y-top 0.0))
  (setq p-out-r-bot (list x-right y-bot 0.0))
  
  ;; 좌측 외곽선 (초록색, 3)
  (entmake (list '(0 . "LINE") '(100 . "AcDbEntity") '(100 . "AcDbLine") (cons 8 layer-name) (cons 62 3) (cons 10 p-out-l-top) (cons 11 p-out-l-bot)))
  ;; 좌측 내부 두께선 (빨간색, 1)
  (entmake (list '(0 . "LINE") '(100 . "AcDbEntity") '(100 . "AcDbLine") (cons 8 layer-name) (cons 62 1) (cons 10 p-in-l-top) (cons 11 p-in-l-bot)))
  ;; 우측 내부 두께선 (빨간색, 1)
  (entmake (list '(0 . "LINE") '(100 . "AcDbEntity") '(100 . "AcDbLine") (cons 8 layer-name) (cons 62 1) (cons 10 p-in-r-top) (cons 11 p-in-r-bot)))
  ;; 우측 외곽선 (초록색, 3)
  (entmake (list '(0 . "LINE") '(100 . "AcDbEntity") '(100 . "AcDbLine") (cons 8 layer-name) (cons 62 3) (cons 10 p-out-r-top) (cons 11 p-out-r-bot)))
  ;; 상단 닫힘 선 (초록색, 3)
  (entmake (list '(0 . "LINE") '(100 . "AcDbEntity") '(100 . "AcDbLine") (cons 8 layer-name) (cons 62 3) (cons 10 p-out-l-top) (cons 11 p-out-r-top)))
  ;; 하단 닫힘 선 (초록색, 3)
  (entmake (list '(0 . "LINE") '(100 . "AcDbEntity") '(100 . "AcDbLine") (cons 8 layer-name) (cons 62 3) (cons 10 p-out-l-bot) (cons 11 p-out-r-bot)))
)

;;;;==========================================================================
;;;; defun draw-section-hpile : 단면 H-Pile, 토류판, 띠장, 지보재(버팀보/잭/앵커), 숏크리트 등 통합 작도
;;;;==========================================================================
(defun draw-section-hpile (start-pt side h b tw tf max-depth embed-depth / layer-name total-len top-len inner-layer-name dir-x cx cy y-top y-bot x-tf exc-y pt-exc-start rock-depth found-rock timber-depth pt-timber-start pt-timber-end pt-timber-bottom-start pt-timber-bottom-end timber-pl hatch-obj sa doc mspace timber-bot-y col-x-pos rock-y pt-debug-start pt-debug-end pt-exc-end s-item s-type s-depth ins-y pt-ins s-ang s-free s-bond ang-rad draw-ang pt-free-end pt-bond-end wale-data wale-h wale-b wale-tw wale-tf wale-dir wale-offset wale-upper-y wale-lower-y wale-upper-insert-pt wale-lower-insert-pt shotcrete-bot-y pt-sc-start pt-sc-end pt-sc-bot-start pt-sc-bot-end sc-pl l-type wale-layer-name pt-ins-wale-base wale-rot-angle jack-block-name jack-insert-x pt-jack-ins jack-rot strut-start-x pt-strut-start strut-end-x pt-strut-end strut-h half-h strut-tf s-jack-type s-sec-str strut-data ep-thick ep-end-x stiff-x1 stiff-x2 brk-p1 brk-p2 brk-p3 brk-p4 p1-x p1-y pt-p1 p2-x p2-y pt-p2 pt-p1-h pt-p2-h face-ang pt-meet p-head-center p-head-1 p-head-2 p-head-3 p-head-4 out-ang pt-anchor-start x-left x-right)

  (setq inner-layer-name (strcat "_H-Pile_" (itoa h) "x" (itoa b) "x" (itoa tw) "-" (itoa tf)))
  (create-layer-if-not-exists inner-layer-name "3")
  (create-layer-if-not-exists "_토류판(timber)" "1")
  (create-layer-if-not-exists "_앵커(Anchor)" "6")
  (create-layer-if-not-exists "_지반선" "8")
  (create-layer-if-not-exists "_숏크리트(shotcrete)" "7")
  (create-layer-if-not-exists "DEBUG_POINT_ANCHOR" "6")
  (create-layer-if-not-exists "DEBUG_POINT_STRUT" "2")
  (create-layer-if-not-exists "DEBUG_POINT_USER" "7")
  (create-layer-if-not-exists "DEBUG_POINT_HPILE" "4")
  
  (setq total-len (* (+ max-depth embed-depth) 1000.0))
  (setq top-len 500.0)
  (setq cx (car start-pt)) (setq cy (cadr start-pt))
  (entmake (list '(0 . "POINT") '(8 . "DEBUG_POINT_USER") '(62 . 7) (cons 10 start-pt)))
  
  (setq exc-y (- cy (* max-depth 1000.0)))
  (setq pt-exc-start (list cx exc-y 0.0))
  (entmake (list '(0 . "POINT") '(8 . "DEBUG_POINT_HPILE") '(62 . 4) (cons 10 pt-exc-start)))
  
  (if (= side "L")
    (setq pt-exc-end (polar pt-exc-start 0.0 30000.0))
    (setq pt-exc-end (polar pt-exc-start pi 30000.0))
  )
  (entmake (list '(0 . "LWPOLYLINE") '(100 . "AcDbEntity") '(100 . "AcDbPolyline") (cons 8 "_지반선") (cons 62 8) '(90 . 2) '(70 . 0) (cons 10 pt-exc-start) (cons 10 pt-exc-end)))
  
  (setq dir-x -1.0) (setq wale-dir 1.0)
  (if (= side "R") (progn (setq dir-x 1.0) (setq wale-dir -1.0)))
  (setq y-top (+ cy top-len)) (setq y-bot (- cy total-len))
  
  ;; 수직 H-Pile 작도 공용 함수 호출
  (setq x-left (min cx (+ cx (* h dir-x))))
  (setq x-right (max cx (+ cx (* h dir-x))))
  (draw-vertical-hpile x-left x-right y-top y-bot tf inner-layer-name)
  
  ;; 토류판 배치를 위한 1차 플랜지 기준 X좌표 산출
  (setq x-tf (+ cx (* tf dir-x)))
  
  (setq wale-data nil)
  (if (and *tsp-wale-spec* (= *tsp-wale-spec* "User-defined") *tsp-wale-custom*)
    (setq wale-data *tsp-wale-custom*)
    (setq wale-data (parse-h-spec *tsp-wale-spec*))
  )
  (if (null wale-data) (setq wale-data '(300 300 10 15)))
  (setq wale-h (nth 0 wale-data)) (setq wale-b (nth 1 wale-data)) (setq wale-tw (nth 2 wale-data)) (setq wale-tf (nth 3 wale-data))
  (setq wale-layer-name "_띠장(Wale)")
  (create-layer-if-not-exists wale-layer-name "3")
  (create-strut-jack-block)
  (create-strut-screw-jack-block)
  
  (if *tsp-support-list*
    (foreach s-item *tsp-support-list*
      (setq s-type (car s-item)) (setq s-depth (cadddr s-item))
      (setq ins-y (- cy (* s-depth 1000.0)))
      (setq pt-ins (list cx ins-y 0.0))
      (cond
        ((wcmatch s-type "앵커*")
          (setq wale-rot-angle (* -0.5 pi wale-dir))
          (setq wale-offset (+ 150.0 (/ wale-b 2.0)))
          (setq wale-upper-insert-pt (list cx (+ ins-y wale-offset) 0.0))
          (draw-wale-section wale-upper-insert-pt wale-rot-angle wale-layer-name wale-h wale-b wale-tw wale-tf 0.0 0.0)
          (setq wale-lower-insert-pt (list cx (- ins-y wale-offset) 0.0))
          (draw-wale-section wale-lower-insert-pt wale-rot-angle wale-layer-name wale-h wale-b wale-tw wale-tf 0.0 0.0)
          (entmake (list '(0 . "POINT") '(8 . "DEBUG_POINT_ANCHOR") '(62 . 6) (cons 10 pt-ins)))
          (setq s-ang (nth 4 s-item)) (setq s-free (nth 5 s-item)) (setq s-bond (nth 6 s-item))
          (setq ang-rad (* s-ang (/ pi 180.0)))
          (if (= side "L") (setq draw-ang (+ pi ang-rad)) (setq draw-ang (- (* 2.0 pi) ang-rad)))
          (setq pt-free-end (polar pt-ins draw-ang (* s-free 1000.0)))
          (setq pt-bond-end (polar pt-free-end draw-ang (* s-bond 1000.0)))
          (setq out-ang (+ draw-ang pi))
          (setq p1-x (+ cx (* wale-h wale-dir)))
          (setq p1-y (+ ins-y wale-offset (/ wale-b 2.0)))
          (setq pt-p1 (list p1-x p1-y 0.0))
          (setq p2-x p1-x)
          (setq p2-y (- ins-y wale-offset (/ wale-b 2.0)))
          (setq pt-p2 (list p2-x p2-y 0.0))
          (setq pt-p1-h (list (+ p1-x (* 100.0 wale-dir)) p1-y 0.0))
          (setq pt-p2-h (list (+ p2-x (* 100.0 wale-dir)) p2-y 0.0))
          (setq face-ang (+ draw-ang (* wale-dir (/ pi 2.0))))
          (setq pt-meet (polar pt-p1-h face-ang 400.0))
          (entmake (list '(0 . "LWPOLYLINE") '(100 . "AcDbEntity") '(100 . "AcDbPolyline")
                         (cons 8 "_앵커(Anchor)") (cons 62 6) '(90 . 5) '(70 . 1)
                         (cons 10 pt-p1) (cons 10 pt-p1-h) (cons 10 pt-meet) (cons 10 pt-p2-h) (cons 10 pt-p2)))
          (setq p-head-center (inters pt-ins pt-free-end pt-p1-h pt-meet nil))
          (if (null p-head-center)
            (setq p-head-center (polar pt-p1-h (angle pt-p1-h pt-meet) 200.0))
          )
          (setq p-head-1 (polar p-head-center face-ang 100.0))
          (setq p-head-2 (polar p-head-center (+ face-ang pi) 100.0))
          (setq p-head-3 (polar p-head-2 out-ang 60.0))
          (setq p-head-4 (polar p-head-1 out-ang 60.0))
          (entmake (list '(0 . "LWPOLYLINE") '(100 . "AcDbEntity") '(100 . "AcDbPolyline")
                         (cons 8 "_앵커(Anchor)") (cons 62 6) '(90 . 4) '(70 . 1)
                         (cons 10 p-head-1) (cons 10 p-head-2) (cons 10 p-head-3) (cons 10 p-head-4)))
          (setq pt-anchor-start (polar p-head-center out-ang 210.0))
          (entmake (list '(0 . "LINE") (cons 8 "_앵커(Anchor)") (cons 62 6) (cons 10 pt-anchor-start) (cons 11 pt-ins)))
          (entmake (list '(0 . "LINE") (cons 8 "_앵커(Anchor)") (cons 62 6) (cons 10 pt-ins) (cons 11 pt-free-end)))
          (entmake (list '(0 . "LWPOLYLINE") '(100 . "AcDbEntity") '(100 . "AcDbPolyline") (cons 8 "_앵커(Anchor)") (cons 62 6) '(90 . 2) '(70 . 0) '(43 . 400.0) (cons 10 (list (car pt-free-end) (cadr pt-free-end))) (cons 10 (list (car pt-bond-end) (cadr pt-bond-end)))))
        )
        ((wcmatch s-type "버팀보*")
        ;; 단일 띠장 및 보걸이 삽입
        (setq wale-rot-angle (* -0.5 pi wale-dir))
        (draw-wale-section pt-ins wale-rot-angle wale-layer-name wale-h wale-b wale-tw wale-tf 0.0 0.0)
          (setq s-jack-type (nth 7 s-item))
          (if (or (null s-jack-type) (= s-jack-type "")) (setq s-jack-type "스크류잭"))
          (if (equal s-jack-type "스크류잭")
            (setq jack-block-name "스크류잭")
            (setq jack-block-name "유압잭")
          )
          (setq jack-insert-x (+ cx (* wale-h wale-dir)))
          (setq pt-jack-ins (list jack-insert-x ins-y 0.0))
          (setq jack-rot (if (> wale-dir 0) 0.0 pi))
          (entmake (list '(0 . "INSERT")
                         (cons 2 jack-block-name)
                         (cons 8 (if (equal jack-block-name "스크류잭") "_스크류잭" "_유압잭"))
                         (cons 62 2)
                         (cons 10 pt-jack-ins)
                         '(41 . 1.0) '(42 . 1.0) '(43 . 1.0)
                         (cons 50 jack-rot)))
          (setq s-sec-str (nth 6 s-item))
          (setq strut-data (parse-h-spec s-sec-str))
          (if (null strut-data) (setq strut-data '(300 300 10 15)))
          (setq strut-h (nth 0 strut-data))
          (setq strut-tf (nth 3 strut-data))
          (setq half-h (/ strut-h 2.0))
          (setq y-top (+ ins-y half-h))
          (setq y-top-in (- y-top strut-tf))
          (setq y-bot (- ins-y half-h))
          (setq y-bot-in (+ y-bot strut-tf))
          (setq x-jack-end (+ jack-insert-x (* 583.0 wale-dir)))
          (setq ep-thick 14.0)
          (setq x-ep-end (+ x-jack-end (* ep-thick wale-dir)))
          (setq stiff-len 200.0)
          (setq stiff-thick 14.0)
          (setq x-stiff-end (+ x-ep-end (* stiff-len wale-dir)))
          (setq x-strut-end (+ x-ep-end (* 4000.0 wale-dir)))
          (entmake (list '(0 . "LWPOLYLINE") '(100 . "AcDbEntity") '(100 . "AcDbPolyline")
                         (cons 8 "_버팀보(Strut)") (cons 62 3) '(90 . 4) '(70 . 1)
                         (cons 10 (list x-jack-end y-top 0.0))
                         (cons 10 (list x-ep-end y-top 0.0))
                         (cons 10 (list x-ep-end y-bot 0.0))
                         (cons 10 (list x-jack-end y-bot 0.0))))
          (setq stiff-y-top (+ ins-y (/ stiff-thick 2.0)))
          (setq stiff-y-bot (- ins-y (/ stiff-thick 2.0)))
          (entmake (list '(0 . "LINE") (cons 8 "_버팀보(Strut)") (cons 62 3)
                         (cons 10 (list x-ep-end stiff-y-top 0.0)) (cons 11 (list x-stiff-end stiff-y-top 0.0))))
          (entmake (list '(0 . "LINE") (cons 8 "_버팀보(Strut)") (cons 62 3)
                         (cons 10 (list x-ep-end stiff-y-bot 0.0)) (cons 11 (list x-stiff-end stiff-y-bot 0.0))))
          (entmake (list '(0 . "LINE") (cons 8 "_버팀보(Strut)") (cons 62 3)
                         (cons 10 (list x-stiff-end stiff-y-top 0.0)) (cons 11 (list x-stiff-end stiff-y-bot 0.0))))
          (entmake (list '(0 . "LINE") (cons 8 "_버팀보(Strut)") (cons 62 3)
                         (cons 10 (list x-ep-end y-top 0.0)) (cons 11 (list x-strut-end y-top 0.0))))
          (entmake (list '(0 . "LINE") (cons 8 "_버팀보(Strut)") (cons 62 3)
                         (cons 10 (list x-ep-end y-bot 0.0)) (cons 11 (list x-strut-end y-bot 0.0))))
          (entmake (list '(0 . "LINE") (cons 8 "_버팀보(Strut)") (cons 62 1)
                         (cons 10 (list x-ep-end y-top-in 0.0)) (cons 11 (list x-strut-end y-top-in 0.0))))
          (entmake (list '(0 . "LINE") (cons 8 "_버팀보(Strut)") (cons 62 1)
                         (cons 10 (list x-ep-end y-bot-in 0.0)) (cons 11 (list x-strut-end y-bot-in 0.0))))
          (setq bulge-val (if (> wale-dir 0) 0.5 -0.5))
          (entmake (list '(0 . "LWPOLYLINE") '(100 . "AcDbEntity") '(100 . "AcDbPolyline")
                         (cons 8 "_버팀보(Strut)") (cons 62 1) '(90 . 5) '(70 . 0)
                         (cons 10 (list x-strut-end y-top 0.0))    (cons 42 0.0)
                         (cons 10 (list x-strut-end y-top-in 0.0)) (cons 42 bulge-val)
                         (cons 10 (list x-strut-end ins-y 0.0))    (cons 42 (- bulge-val))
                         (cons 10 (list x-strut-end y-bot-in 0.0)) (cons 42 0.0)
                         (cons 10 (list x-strut-end y-bot 0.0))))
        )
      )
    )
  )
  
  ;; 공용 함수를 이용하여 암반 심도 확보
  (setq rock-depth (tsp-get-rock-start-depth))
  
  (if rock-depth
    (if (>= rock-depth max-depth)
        (progn (setq timber-bot-y exc-y) (setq shotcrete-bot-y nil))
        (progn (setq timber-bot-y (- cy (* rock-depth 1000.0))) (setq shotcrete-bot-y exc-y))
    )
    (progn (setq timber-bot-y exc-y) (setq shotcrete-bot-y nil))
  )
  
  (setq pt-timber-start (list x-tf cy 0.0))
  (setq pt-timber-end (list (+ x-tf (* *tsp-timber-thickness* dir-x)) cy 0.0))
  (setq pt-timber-bottom-end (list (car pt-timber-end) timber-bot-y 0.0))
  (setq pt-timber-bottom-start (list (car pt-timber-start) timber-bot-y 0.0))
  (entmake (list '(0 . "LWPOLYLINE") '(100 . "AcDbEntity") '(100 . "AcDbPolyline") (cons 8 "_토류판(timber)") (cons 62 1) '(90 . 4) '(70 . 1) (cons 10 pt-timber-start) (cons 10 pt-timber-end) (cons 10 pt-timber-bottom-end) (cons 10 pt-timber-bottom-start)))
  (setq timber-pl (entlast))
  (setq doc (vla-get-activedocument (vlax-get-acad-object)))
  (if (= (getvar "CVPORT") 1)
    (setq mspace (vla-get-paperspace doc))
    (setq mspace (vla-get-modelspace doc))
  )
  (if timber-pl (progn
      (setq hatch-obj (vla-addhatch mspace 1 "ANSI31" :vlax-true))
      (vla-put-patternscale hatch-obj (* 100.0 (get-hatch-scale-factor)))
      (vla-put-patternangle hatch-obj (* 135.0 (/ pi 180.0)))
      (vla-put-layer hatch-obj "_토류판(timber)")
      (vla-put-color hatch-obj 1)
      (setq sa (vlax-make-safearray 9 (cons 0 0)))
      (vlax-safearray-fill sa (list (vlax-ename->vla-object timber-pl)))
      (vla-appendouterloop hatch-obj sa)
      (vla-evaluate hatch-obj)))
      
  (if shotcrete-bot-y
    (progn
      (setq pt-sc-start (list cx timber-bot-y 0.0))
      (setq pt-sc-end (list (+ cx (* *tsp-shotcrete-thick* dir-x)) timber-bot-y 0.0))
      (setq pt-sc-bot-end (list (car pt-sc-end) shotcrete-bot-y 0.0))
      (setq pt-sc-bot-start (list (car pt-sc-start) shotcrete-bot-y 0.0))
      (entmake (list '(0 . "LWPOLYLINE") '(100 . "AcDbEntity") '(100 . "AcDbPolyline") (cons 8 "_숏크리트(shotcrete)") (cons 62 7) '(90 . 4) '(70 . 1) (cons 10 pt-sc-start) (cons 10 pt-sc-end) (cons 10 pt-sc-bot-end) (cons 10 pt-sc-bot-start)))
      (setq sc-pl (entlast))
      (if sc-pl (progn
          (setq hatch-obj (vla-addhatch mspace 1 "AR-CONC" :vlax-true))
          (vla-put-patternscale hatch-obj (* 2.0 (get-hatch-scale-factor)))
          (vla-put-patternangle hatch-obj 0.0)
          (vla-put-layer hatch-obj "_숏크리트(shotcrete)")
          (vla-put-color hatch-obj 7)
          (setq sa (vlax-make-safearray 9 (cons 0 0)))
          (vlax-safearray-fill sa (list (vlax-ename->vla-object sc-pl)))
          (vla-appendouterloop hatch-obj sa)
          (vla-evaluate hatch-obj)))
    )
  )
  (princ "\n단면 H-Pile 작도 완료.")
)

;;;;==========================================================================
;;;; defun draw-section-cip : CIP 단면도 생성
;;;;==========================================================================
;; 변수명 통일: exc-depth -> max-depth
(defun draw-section-cip (start-pt side max-depth embed-depth support-list / total-depth h-b h-h h-t1 h-t2 cip-dia grout-dia wale-insert-x bracket-width p1 p2 p3 p4 obj-grout obj-grout-hatch obj-cip s-item s-type s-depth ins-y pt-ins br-p1 br-p2 br-p3 br-p4 hp-layer old-osmode wale-data wale-h wale-b wale-tw wale-tf wale-layer-name wale-dir wale-rot-angle wale-offset wale-upper-insert-pt wale-lower-insert-pt s-ang s-free s-bond ang-rad draw-ang pt-free-end pt-bond-end out-ang p1-x p1-y pt-p1 p2-x p2-y pt-p2 pt-p1-h pt-p2-h face-ang pt-meet p-head-center p-head-1 p-head-2 p-head-3 p-head-4 pt-anchor-start s-jack-type jack-block-name jack-insert-x pt-jack-ins jack-rot s-sec-str strut-data strut-h strut-tf half-h y-top y-top-in y-bot y-bot-in x-jack-end ep-thick x-ep-end stiff-len stiff-thick x-stiff-end x-strut-end stiff-y-top stiff-y-bot bulge-val cx cy real-cx x-left x-right dir-x exc-y pt-exc-start pt-exc-end x-grout-start x-grout-end water-lvl rock-depth grout-depth-mm)

  ;; OSNAP 끄기 (작도 중 스냅 간섭 방지)
  (setq old-osmode (getvar "OSMODE"))
  (setvar "OSMODE" 0)

  ;; 1. 제원 및 치수 설정
  (setq total-depth (* (+ max-depth embed-depth) 1000.0))

  ;; 방향 변수 및 좌표 분리
  (setq cx (car start-pt) cy (cadr start-pt))
  (setq dir-x -1.0) (setq wale-dir 1.0)
  (if (= side "R") (progn (setq dir-x 1.0) (setq wale-dir -1.0)))

  ;; CIP 및 그라우팅 규격
  (setq cip-dia (if (type *tsp-cip-dia*) *tsp-cip-dia* (atof (if *tsp-cip-dia* *tsp-cip-dia* "500"))))
  (setq grout-dia (if (and *tsp-cip-grouting-idx* (= *tsp-cip-grouting-idx* "1")) 600.0 200.0))

  ;; 실제 중심축(real-cx) 계산
  (setq real-cx (+ cx (* (/ cip-dia 2.0) dir-x)))

  ;; 굴착바닥고 생성 로직
  (setq exc-y (- cy (* max-depth 1000.0)))
  (setq pt-exc-start (list cx exc-y 0.0))
  (if (= side "L")
    (setq pt-exc-end (polar pt-exc-start 0.0 30000.0))
    (setq pt-exc-end (polar pt-exc-start pi 30000.0))
  )
  
  ;; 도면층 자동 생성 내부 함수
  (defun make-layer-if-not-exist (layname col)
    (if (not (tblsearch "LAYER" layname))
      (command "_.-layer" "_m" layname "_c" col "" "")
    )
  )

  (make-layer-if-not-exist "_지반선" "8")
  (entmake (list '(0 . "LWPOLYLINE") '(100 . "AcDbEntity") '(100 . "AcDbPolyline") (cons 8 "_지반선") (cons 62 8) '(90 . 2) '(70 . 0) (cons 10 pt-exc-start) (cons 10 pt-exc-end)))

  ;; H-Pile 규격 추출
  (setq h-b  (nth 0 *tsp-h-pile-size*)
        h-h  (nth 1 *tsp-h-pile-size*)
        h-t1 (nth 2 *tsp-h-pile-size*)
        h-t2 (nth 3 *tsp-h-pile-size*))

  (setq wale-insert-x cx)
  (setq bracket-width (/ (- cip-dia h-h) 2.0))

  ;; 2. 지하수위 판별 및 암반 심도 탐색 (공용 함수 사용)
  (setq water-lvl 999.0)
  (if (and (boundp '*tsp-water-chk*) (= *tsp-water-chk* "1") (boundp '*tsp-water-depth*))
    (cond
      ((numberp *tsp-water-depth*) (setq water-lvl *tsp-water-depth*))
      ((= (type *tsp-water-depth*) 'STR) (setq water-lvl (atof *tsp-water-depth*)))
    )
  )

  (setq rock-start-depth (tsp-get-rock-start-depth))

  ;; 3. CIP 하단 심도 결정 (숏크리트 적용 여부 판별)
  (setq cip-bottom-mm total-depth) ; 기본값: 전체 심도
  (setq shotcrete-bot-y nil)

  (if rock-start-depth
    (progn
      ;; 사용자 입력 암반 근입 깊이 (문자열->실수 변환, 단위: mm)
      ;; *tsp-cip-rock-embed* 에서 *tsp-rock-embed* 공통 변수로 통일
      (setq user-embed-mm (if (and (boundp '*tsp-rock-embed*) *tsp-rock-embed* (/= *tsp-rock-embed* "")) 
                              (atof *tsp-rock-embed*) 
                              500.0))
      
      (setq rock-y (- cy (* rock-start-depth 1000.0)))
      (setq calc-cip-bot-y (- rock-y user-embed-mm))
      
      ;; 근입 깊이를 더한 마감고가 굴착 바닥면(exc-y)을 뚫고 내려가면 굴착 바닥면으로 제한
      (if (< calc-cip-bot-y exc-y) 
        (setq calc-cip-bot-y exc-y)
      )
      
      ;; 굴착 심도가 암반 시작점보다 깊을 때만 숏크리트 적용
      (if (> max-depth rock-start-depth)
        (progn
          (setq cip-bottom-mm (- cy calc-cip-bot-y)) ; 도면용 cy 기준 상대길이로 재변환
          (setq shotcrete-bot-y exc-y) ; 숏크리트는 CIP 마감선부터 굴착 바닥면까지
        )
      )
    )
  )

  ;; 4. 그라우팅 단면 작도 (지하수위 있을때만)
  (if (> max-depth water-lvl)
    (progn
      (make-layer-if-not-exist "_그라우팅" "5")
      (setvar "clayer" "_그라우팅")
      
      (setq x-grout-start (+ real-cx (* (/ h-h 2.0) dir-x)))
      (setq x-grout-end (+ x-grout-start (* grout-dia dir-x)))
      ;; 그라우팅도 재계산된 cip-bottom-mm을 따름
      (setq p1 (list x-grout-end cy))
      (setq p2 (list x-grout-start cy))
      (setq p3 (list (car p2) (- cy cip-bottom-mm)))
      (setq p4 (list (car p1) (- cy cip-bottom-mm)))

      (command "_.pline" p1 p2 p3 p4 "_c")
      (setq obj-grout (entlast))
      (setq old-hpannotative (getvar "HPANNOTATIVE"))
      (if old-hpannotative (setvar "HPANNOTATIVE" 0))
      
      (command "_.hatch" "AR-SAND" (* 6.0 (get-hatch-scale-factor)) 0 obj-grout "")
      
      (if old-hpannotative (setvar "HPANNOTATIVE" old-hpannotative))
      (setq old-hpannotative nil)
      (setq obj-grout-hatch (entlast))
    )
    (progn
      (setq obj-grout nil)
      (setq obj-grout-hatch nil)
    )
  )

  ;; 5. CIP 콘크리트 단면 작도
  (make-layer-if-not-exist "_CIP" "7")
  (setvar "clayer" "_CIP")
  (setq p1 (list (- real-cx (/ cip-dia 2.0)) cy))
  (setq p2 (list (+ real-cx (/ cip-dia 2.0)) cy))
  (setq p3 (list (car p2) (- cy cip-bottom-mm)))
  (setq p4 (list (car p1) (- cy cip-bottom-mm)))

  (command "_.pline" p1 p2 p3 p4 "_c")
  (setq obj-cip (entlast))
  (setq old-hpannotative (getvar "HPANNOTATIVE"))
  (if old-hpannotative (setvar "HPANNOTATIVE" 0))
  
  (command "_.hatch" "AR-CONC" (* 6.0 (get-hatch-scale-factor)) 0 obj-cip "")
  
  (if old-hpannotative (setvar "HPANNOTATIVE" old-hpannotative))
  (setq old-hpannotative nil)
  
  (if (and obj-grout obj-grout-hatch)
    (command "_.draworder" obj-grout obj-grout-hatch "" "_f")
  )

  ;; 6. H-Pile 단면 작도 (real-cx 기준)
  (setq hp-layer (strcat "_H-Pile_" (rtos h-b 2 0) "x" (rtos h-h 2 0) "x" (rtos h-t1 2 0) "-" (rtos h-t2 2 0)))
  (make-layer-if-not-exist hp-layer "3")
  
  (setq y-top cy)
  (setq y-bot (- cy total-depth)) ; 내부 심재 H-Pile은 암반 상관없이 무조건 바닥(전체심도)까지
  (setq x-left (- real-cx (/ h-h 2.0)))
  (setq x-right (+ real-cx (/ h-h 2.0)))

  (draw-vertical-hpile x-left x-right y-top y-bot h-t2 hp-layer)

  ;; 7. 숏크리트 단면 작도
  (if shotcrete-bot-y
    (progn
      (make-layer-if-not-exist "_숏크리트(shotcrete)" "7")
      (setvar "clayer" "_숏크리트(shotcrete)")
      (setq sc-start-y (- cy cip-bottom-mm))
      
      (setq sc-base-x (+ real-cx (* (/ h-h 2.0) (* dir-x -1.0))))
      
      (setq pt-sc-start (list sc-base-x sc-start-y 0.0))
      (setq pt-sc-end (list (+ sc-base-x (* (if (and (boundp '*tsp-shotcrete-thick*) *tsp-shotcrete-thick*) *tsp-shotcrete-thick* 100.0) dir-x)) sc-start-y 0.0))
      
      (setq pt-sc-bot-end (list (car pt-sc-end) shotcrete-bot-y 0.0))
      (setq pt-sc-bot-start (list (car pt-sc-start) shotcrete-bot-y 0.0))

      (entmake (list '(0 . "LWPOLYLINE") '(100 . "AcDbEntity") '(100 . "AcDbPolyline") 
                     (cons 8 "_숏크리트(shotcrete)") (cons 62 7) '(90 . 4) '(70 . 1) 
                     (cons 10 pt-sc-start) (cons 10 pt-sc-end) (cons 10 pt-sc-bot-end) (cons 10 pt-sc-bot-start)))
      (setq sc-pl (entlast))

      (if sc-pl
        (progn
          (setq old-hpannotative (getvar "HPANNOTATIVE"))
          (if old-hpannotative (setvar "HPANNOTATIVE" 0))
          (command "_.hatch" "AR-CONC" (* 2.0 (get-hatch-scale-factor)) 0 sc-pl "")
          (if old-hpannotative (setvar "HPANNOTATIVE" old-hpannotative))
        )
      )

      (make-layer-if-not-exist "_지반선" "8")
      (entmake (list '(0 . "LINE") 
                     (cons 8 "_지반선") 
                     (cons 62 8) 
                     (cons 10 pt-sc-bot-start)
                     (cons 11 (list cx shotcrete-bot-y 0.0))))
    )
  )

  ;; 5. 지보재 및 브래킷 작도 루프
  (setq wale-data nil)
  (if (and *tsp-wale-spec* (= *tsp-wale-spec* "User-defined") *tsp-wale-custom*)
    (setq wale-data *tsp-wale-custom*)
    (setq wale-data (parse-h-spec *tsp-wale-spec*))
  )
  (if (null wale-data) (setq wale-data '(300 300 10 15)))
  (setq wale-h (nth 0 wale-data) wale-b (nth 1 wale-data) wale-tw (nth 2 wale-data) wale-tf (nth 3 wale-data))

  (setq wale-layer-name "_띠장(Wale)")
  (make-layer-if-not-exist wale-layer-name "3")
  (make-layer-if-not-exist "_앵커(Anchor)" "6")
  (make-layer-if-not-exist "_버팀보(Strut)" "3")
  (make-layer-if-not-exist "_브래킷(bracket)" "8")

  (create-strut-jack-block)
  (create-strut-screw-jack-block)

  (foreach s-item support-list
    (setq s-type (car s-item))
    (setq s-depth (cadddr s-item))
    (setq ins-y (- cy (* s-depth 1000.0)))
    (setq pt-ins (list wale-insert-x ins-y 0.0))

    (cond
      ((wcmatch s-type "앵커*")
        (setq wale-rot-angle (* -0.5 pi wale-dir))
        (setq wale-offset (+ 150.0 (/ wale-b 2.0)))

        ;; 앵커용 쌍띠장 브래킷 2개 작도
        (foreach center-y (list (+ ins-y wale-offset) (- ins-y wale-offset))
          (setvar "clayer" "_브래킷(Bracket)")
          (setq br-p1 (list (+ real-cx (* (/ h-h 2.0) wale-dir)) (+ center-y (/ wale-b 2.0))))
          (setq br-p2 (list wale-insert-x (+ center-y (/ wale-b 2.0))))
          (setq br-p3 (list (car br-p2) (- center-y (/ wale-b 2.0))))
          (setq br-p4 (list (car br-p1) (- center-y (/ wale-b 2.0))))
          (command "_.pline" br-p1 br-p2 br-p3 br-p4 "_c")
          (command "_.hatch" "ANSI31" (if (= (getvar "MEASUREMENT") 0) 400.0 20.0) 90 (entlast) "")
        )
        
        ;; 상/하 띠장 삽입
        (setq wale-upper-insert-pt (list wale-insert-x (+ ins-y wale-offset) 0.0))
        (draw-wale-section wale-upper-insert-pt wale-rot-angle wale-layer-name wale-h wale-b wale-tw wale-tf 0.0 bracket-width)
        (setq wale-lower-insert-pt (list wale-insert-x (- ins-y wale-offset) 0.0))
        (draw-wale-section wale-lower-insert-pt wale-rot-angle wale-layer-name wale-h wale-b wale-tw wale-tf 0.0 bracket-width)
        
        ;; 앵커 본체 작도 로직
        (entmake (list '(0 . "POINT") '(8 . "DEBUG_POINT_ANCHOR") '(62 . 6) (cons 10 pt-ins)))
        (setq s-ang (nth 4 s-item) s-free (nth 5 s-item) s-bond (nth 6 s-item))
        (setq ang-rad (* s-ang (/ pi 180.0)))
        (setq draw-ang (+ pi ang-rad)) 
        (setq pt-free-end (polar pt-ins draw-ang (* s-free 1000.0)))
        (setq pt-bond-end (polar pt-free-end draw-ang (* s-bond 1000.0)))
        (setq out-ang (+ draw-ang pi))
        (setq p1-x (+ wale-insert-x (* wale-h wale-dir)))
        (setq p1-y (+ ins-y wale-offset (/ wale-b 2.0)))
        (setq pt-p1 (list p1-x p1-y 0.0))
        (setq p2-x p1-x)
        (setq p2-y (- ins-y wale-offset (/ wale-b 2.0)))
        (setq pt-p2 (list p2-x p2-y 0.0))
        (setq pt-p1-h (list (+ p1-x (* 100.0 wale-dir)) p1-y 0.0))
        (setq pt-p2-h (list (+ p2-x (* 100.0 wale-dir)) p2-y 0.0))
        (setq face-ang (+ draw-ang (* wale-dir (/ pi 2.0))))
        (setq pt-meet (polar pt-p1-h face-ang 400.0))
        (entmake (list '(0 . "LWPOLYLINE") '(100 . "AcDbEntity") '(100 . "AcDbPolyline")
                       (cons 8 "_앵커(Anchor)") (cons 62 6) '(90 . 5) '(70 . 1)
                       (cons 10 pt-p1) (cons 10 pt-p1-h) (cons 10 pt-meet) (cons 10 pt-p2-h) (cons 10 pt-p2)))
        (setq p-head-center (inters pt-ins pt-free-end pt-p1-h pt-meet nil))
        (if (null p-head-center) (setq p-head-center (polar pt-p1-h (angle pt-p1-h pt-meet) 200.0)))
        (setq p-head-1 (polar p-head-center face-ang 100.0))
        (setq p-head-2 (polar p-head-center (+ face-ang pi) 100.0))
        (setq p-head-3 (polar p-head-2 out-ang 60.0))
        (setq p-head-4 (polar p-head-1 out-ang 60.0))
        (entmake (list '(0 . "LWPOLYLINE") '(100 . "AcDbEntity") '(100 . "AcDbPolyline")
                       (cons 8 "_앵커(Anchor)") (cons 62 6) '(90 . 4) '(70 . 1)
                       (cons 10 p-head-1) (cons 10 p-head-2) (cons 10 p-head-3) (cons 10 p-head-4)))
        (setq pt-anchor-start (polar p-head-center out-ang 210.0))
        (entmake (list '(0 . "LINE") (cons 8 "_앵커(Anchor)") (cons 62 6) (cons 10 pt-anchor-start) (cons 11 pt-ins)))
        (entmake (list '(0 . "LINE") (cons 8 "_앵커(Anchor)") (cons 62 6) (cons 10 pt-ins) (cons 11 pt-free-end)))
        (entmake (list '(0 . "LWPOLYLINE") '(100 . "AcDbEntity") '(100 . "AcDbPolyline") 
                       (cons 8 "_앵커(Anchor)") (cons 62 6) '(90 . 2) '(70 . 0) '(43 . 400.0) 
                       (cons 10 (list (car pt-free-end) (cadr pt-free-end))) 
                       (cons 10 (list (car pt-bond-end) (cadr pt-bond-end)))))
      )
      
      ((wcmatch s-type "버팀보*")
        ;; 버팀보용 단일 브래킷 작도
        (setvar "clayer" "_브래킷(Bracket)")
        (setq br-p1 (list (+ real-cx (* (/ h-h 2.0) wale-dir)) (+ ins-y (/ wale-b 2.0))))
        (setq br-p2 (list wale-insert-x (+ ins-y (/ wale-b 2.0))))
        (setq br-p3 (list (car br-p2) (- ins-y (/ wale-b 2.0))))
        (setq br-p4 (list (car br-p1) (- ins-y (/ wale-b 2.0))))
        (command "_.pline" br-p1 br-p2 br-p3 br-p4 "_c")
        (command "_.hatch" "ANSI31" (if (= (getvar "MEASUREMENT") 0) 400.0 20.0) 90 (entlast) "")

        ;; 단일 띠장 및 보걸이 삽입
        (setq wale-rot-angle (* -0.5 pi wale-dir))
        (draw-wale-section pt-ins wale-rot-angle wale-layer-name wale-h wale-b wale-tw wale-tf 150.0 bracket-width)
        
        ;; 버팀보 본체 작도 로직
        (setq s-jack-type (nth 7 s-item))
        (if (or (null s-jack-type) (= s-jack-type "")) (setq s-jack-type "스크류잭"))
        (if (equal s-jack-type "스크류잭") (setq jack-block-name "스크류잭") (setq jack-block-name "유압잭"))
        (setq jack-insert-x (+ wale-insert-x (* wale-h wale-dir)))
        (setq pt-jack-ins (list jack-insert-x ins-y 0.0))
        (setq jack-rot (if (> wale-dir 0) 0.0 pi))
        (entmake (list '(0 . "INSERT") (cons 2 jack-block-name) 
                       (cons 8 (if (equal jack-block-name "스크류잭") "_스크류잭" "_유압잭")) 
                       (cons 62 2) (cons 10 pt-jack-ins) '(41 . 1.0) '(42 . 1.0) '(43 . 1.0) (cons 50 jack-rot)))
        (setq s-sec-str (nth 6 s-item))
        (setq strut-data (parse-h-spec s-sec-str))
        (if (null strut-data) (setq strut-data '(300 300 10 15)))
        (setq strut-h (nth 0 strut-data) strut-tf (nth 3 strut-data) half-h (/ strut-h 2.0))
        (setq y-top (+ ins-y half-h) y-top-in (- y-top strut-tf) y-bot (- ins-y half-h) y-bot-in (+ y-bot strut-tf))
        (setq x-jack-end (+ jack-insert-x (* 583.0 wale-dir)) ep-thick 14.0 x-ep-end (+ x-jack-end (* ep-thick wale-dir)))
        (setq stiff-len 200.0 stiff-thick 14.0 x-stiff-end (+ x-ep-end (* stiff-len wale-dir)) x-strut-end (+ x-ep-end (* 4000.0 wale-dir)))
        (entmake (list '(0 . "LWPOLYLINE") '(100 . "AcDbEntity") '(100 . "AcDbPolyline") 
                       (cons 8 "_버팀보(Strut)") (cons 62 3) '(90 . 4) '(70 . 1) 
                       (cons 10 (list x-jack-end y-top 0.0)) (cons 10 (list x-ep-end y-top 0.0)) 
                       (cons 10 (list x-ep-end y-bot 0.0)) (cons 10 (list x-jack-end y-bot 0.0))))
        (setq stiff-y-top (+ ins-y (/ stiff-thick 2.0)) stiff-y-bot (- ins-y (/ stiff-thick 2.0)))
        (entmake (list '(0 . "LINE") (cons 8 "_버팀보(Strut)") (cons 62 3) (cons 10 (list x-ep-end stiff-y-top 0.0)) (cons 11 (list x-stiff-end stiff-y-top 0.0))))
        (entmake (list '(0 . "LINE") (cons 8 "_버팀보(Strut)") (cons 62 3) (cons 10 (list x-ep-end stiff-y-bot 0.0)) (cons 11 (list x-stiff-end stiff-y-bot 0.0))))
        (entmake (list '(0 . "LINE") (cons 8 "_버팀보(Strut)") (cons 62 3) (cons 10 (list x-stiff-end stiff-y-top 0.0)) (cons 11 (list x-stiff-end stiff-y-bot 0.0))))
        (entmake (list '(0 . "LINE") (cons 8 "_버팀보(Strut)") (cons 62 3) (cons 10 (list x-ep-end y-top 0.0)) (cons 11 (list x-strut-end y-top 0.0))))
        (entmake (list '(0 . "LINE") (cons 8 "_버팀보(Strut)") (cons 62 3) (cons 10 (list x-ep-end y-bot 0.0)) (cons 11 (list x-strut-end y-bot 0.0))))
        (entmake (list '(0 . "LINE") (cons 8 "_버팀보(Strut)") (cons 62 1) (cons 10 (list x-ep-end y-top-in 0.0)) (cons 11 (list x-strut-end y-top-in 0.0))))
        (entmake (list '(0 . "LINE") (cons 8 "_버팀보(Strut)") (cons 62 1) (cons 10 (list x-ep-end y-bot-in 0.0)) (cons 11 (list x-strut-end y-bot-in 0.0))))
        (setq bulge-val (if (> wale-dir 0) 0.5 -0.5))
        (entmake (list '(0 . "LWPOLYLINE") '(100 . "AcDbEntity") '(100 . "AcDbPolyline") 
                       (cons 8 "_버팀보(Strut)") (cons 62 1) '(90 . 5) '(70 . 0) 
                       (cons 10 (list x-strut-end y-top 0.0)) (cons 42 0.0) 
                       (cons 10 (list x-strut-end y-top-in 0.0)) (cons 42 bulge-val) 
                       (cons 10 (list x-strut-end ins-y 0.0)) (cons 42 (- bulge-val)) 
                       (cons 10 (list x-strut-end y-bot-in 0.0)) (cons 42 0.0) 
                       (cons 10 (list x-strut-end y-bot 0.0))))
      )
    )
  )

  ;; 시스템 변수 복구
  (setvar "OSMODE" old-osmode)
  (princ)
)


;;;;==========================================================================
;;;; defun create-strut-jack-block : 유압잭 형상을 블록으로 정의
;;;;==========================================================================
(defun create-strut-jack-block (/ block-name layer-name _v _pline)
  (setq block-name "유압잭")
  (setq layer-name "_유압잭")
  ;; 1. 레이어 생성 (노란색: 2번)
  (create-layer-if-not-exists layer-name "2")
  ;; 2. 블록 정의 (없는 경우에만 생성)
  (if (not (tblsearch "BLOCK" block-name))
    (progn
      ;; 블록 정의 시작 (기준점 0,0,0)
      (entmake (list '(0 . "BLOCK") (cons 2 block-name) '(70 . 0) '(10 0.0 0.0 0.0))) 

      (defun _v (dx dy) (list dx dy))


;;;;==========================================================================
;;;; defun _pline : [내부 헬퍼 함수] 폴리라인 생성 (레이어: _유압잭, 색상: ByLayer)
;;;;==========================================================================
      (defun _pline (pts closed / lst)
        (setq lst (list '(0 . "LWPOLYLINE")
                        '(100 . "AcDbEntity")
                        '(100 . "AcDbPolyline")
                        (cons 8 layer-name)  ;; 요청하신 레이어 적용
                        (cons 62 256)        ;; ByLayer (레이어가 노랑이므로 노랑으로 나옴)
                        (cons 90 (length pts))
                        (cons 70 (if closed 1 0))))
        (foreach p pts
          (setq lst (append lst (list (cons 10 p))))
          (if (> (length p) 2) (setq lst (append lst (list (cons 42 (caddr p))))))
        )
        (entmake lst)
      )
      ;; 잭 형상 작도
      (_pline (list (_v 0 150) (_v 15 150) (_v 15 -150) (_v 0 -150)) T)
      (_pline (list (_v 568 150) (_v 583 150) (_v 583 -150) (_v 568 -150)) T)
      (_pline (list (_v 15 150) (_v 160 85)) nil)
      (_pline (list (_v 15 -150) (_v 160 -85)) nil)
      (_pline (list (_v 15 85) (_v 375 85)) nil)
      (_pline (list (_v 15 -85) (_v 375 -85)) nil)
      (_pline (list (_v 375 85) (_v 375 -85)) nil)
      (_pline (list (_v 15 7) (_v 160 7)) nil)
      (_pline (list (_v 15 -7) (_v 160 -7)) nil)
      (_pline (list (_v 160 7) (_v 160 -7)) nil)
      (_pline (list (_v 446 55) (append (_v 496 55) '(0.102)) (_v 568 70)) nil)
      (_pline (list (_v 568 150) (_v 446 55)) nil)
      (_pline (list (_v 446 -55) (append (_v 496 -55) '(-0.102)) (_v 568 -70)) nil)
      (_pline (list (_v 568 -150) (_v 446 -55)) nil)
      (_pline (list (_v 446 7) (_v 568 7)) nil)
      (_pline (list (_v 445 -7) (_v 568 -7)) nil)
      (_pline (list (_v 400 75) (_v 400 95) (_v 420 95) (_v 420 75)) nil)
      (_pline (list (_v 400 10) (_v 420 10) (_v 420 -10) (_v 400 -10)) T)
      (_pline (list (_v 400 -75) (_v 400 -95) (_v 420 -95) (_v 420 -75)) nil)
      (_pline (list (_v 375 75) (_v 446 75)) nil)
      (_pline (list (_v 375 -75) (_v 446 -75)) nil)
      (_pline (list (_v 446 75) (_v 446 -75)) nil)
      ;; 기준점 및 끝점 포인트 (디버깅용, 필요 시 삭제 가능)
      (entmake (list '(0 . "POINT") (cons 8 layer-name) (cons 10 '(0 0 0))))
      (entmake (list '(0 . "POINT") (cons 8 layer-name) (cons 10 '(583 0 0))))
      (entmake (list '(0 . "ENDBLK"))) ;; 블록 정의 종료
    )
  )
  block-name ;; 블록 이름 반환
)


;;;;==========================================================================
;;;; defun create-strut-screw-jack-block : 스크류잭 형상을 블록으로 정의
;;;;==========================================================================
(defun create-strut-screw-jack-block (/ block-name layer-name _v _pline)
  (setq block-name "스크류잭")
  (setq layer-name "_스크류잭")
  ;; 1. 레이어 생성 (노란색: 2번)
  (create-layer-if-not-exists layer-name "2")
  ;; 2. 블록 정의 (없는 경우에만 생성)
  (if (not (tblsearch "BLOCK" block-name))
    (progn
      (entmake (list '(0 . "BLOCK") (cons 2 block-name) '(70 . 0) '(10 0.0 0.0 0.0)))
      ;; [좌표 보정 함수]
      ;; 원본은 중심(0) 기준 -291.5 ~ +291.5 이므로,
      ;; 시작점을 0으로 맞추기 위해 X에 291.5를 더해줍니다.

      (defun _v (dx dy) (list (+ dx 291.5) dy))


;;;;==========================================================================
;;;; defun _pline : 자동 정리된 함수
;;;;==========================================================================
      (defun _pline (pts closed / lst)
        (setq lst (list '(0 . "LWPOLYLINE")
                        '(100 . "AcDbEntity")
                        '(100 . "AcDbPolyline")
                        (cons 8 layer-name)
                        (cons 62 256)
                        (cons 90 (length pts))
                        (cons 70 (if closed 1 0))))
        (foreach p pts (setq lst (append lst (list (cons 10 p)))))
        (entmake lst)
      )
      ;; --- 스크류잭 형상 (사용자 정의 + 좌표보정) ---
      (entmake (list '(0 . "CIRCLE") (cons 8 layer-name) (cons 62 256) (cons 10 (_v 0 0)) (cons 40 7.0)))
      (_pline (list (_v -22.5 50) (_v 22.5 50) (_v 22.5 -50) (_v -22.5 -50)) T)
      (_pline (list (_v -7 50) (_v -7 100) (_v 7 100) (_v 7 50)) nil)
      (_pline (list (_v -7 -50) (_v -7 -100) (_v 7 -100) (_v 7 -50)) nil)
      (_pline (list (_v -57.5 25) (_v -22.5 25)) nil)
      (_pline (list (_v -57.5 -25) (_v -22.5 -25)) nil)
      (_pline (list (_v 57.5 25) (_v 22.5 25)) nil)
      (_pline (list (_v 57.5 -25) (_v 22.5 -25)) nil)
      (_pline (list (_v -97.5 50) (_v -57.5 50) (_v -57.5 -50) (_v -97.5 -50)) nil)
      (_pline (list (_v 97.5 50) (_v 57.5 50) (_v 57.5 -50) (_v 97.5 -50)) nil)
      (_pline (list (_v -277.5 70) (_v -97.5 70) (_v -97.5 -70) (_v -277.5 -70)) nil)
      (_pline (list (_v 277.5 70) (_v 97.5 70) (_v 97.5 -70) (_v 277.5 -70)) nil)
      (_pline (list (_v -277.5 7) (_v -132.5 7) (_v -132.5 -7) (_v -277.5 -7)) nil)
      (_pline (list (_v 277.5 7) (_v 132.5 7) (_v 132.5 -7) (_v 277.5 -7)) nil)
      (_pline (list (_v -291.5 150) (_v -277.5 150) (_v -277.5 -150) (_v -291.5 -150)) T)
      (_pline (list (_v 291.5 150) (_v 277.5 150) (_v 277.5 -150) (_v 291.5 -150)) T)
      (_pline (list (_v -277.5 150) (_v -132.5 95) (_v -132.5 70)) nil)
      (_pline (list (_v 277.5 150) (_v 132.5 95) (_v 132.5 70)) nil)
      (_pline (list (_v -277.5 -150) (_v -132.5 -95) (_v -132.5 -70)) nil)
      (_pline (list (_v 277.5 -150) (_v 132.5 -95) (_v 132.5 -70)) nil)
      (entmake (list '(0 . "POINT") (cons 8 layer-name) (cons 10 (_v -291.5 0))))
      (entmake (list '(0 . "ENDBLK")))
    )
  )
  block-name
)


;;;;==========================================================================
;;;; defun draw-section-ground-line : 단면도 그리기 메인 진입점 (지반선 그리기 및 UCS 변환)
;;;;==========================================================================
(defun draw-section-ground-line (dcl-path selected-idx / loop-choice side start-pt end-pt layer-name ltype-name pt1 pt2 h-spec-list h b tw tf draw-success)
  (setq *tsp-cancel-flag* nil) ; 취소 신호 초기화
  (setq loop-choice T)
  (setq draw-success nil)
  
  ;; 좌/우/단면정의 선택 무한 루프
  (while loop-choice
    (initget "L R S")
    (setq side (vl-catch-all-apply 'getkword (list "\n단면선택 [좌측반단면(L) / 우측반단면(R) / 단면정의(S)] <L>: ")))
    (if (vl-catch-all-error-p side)
      (progn (setq side nil loop-choice nil *tsp-cancel-flag* T)) ;; ESC 누르면 종료
      (progn
        (if (or (null side) (= side "")) (setq side "L"))
        (if (= side "S")
          (progn
            ;; 단면정의 창 호출 및 데이터 갱신
            (princ "\n[단면정의] 지반 정보를 수정합니다.")
            (if (= (soil-dialog-callback dcl-path) 1)
              (progn
                ;; 확인을 누르면 수정한 데이터를 현재 세그먼트에 완벽히 덮어쓰기
                (sync-globals-to-segment selected-idx)
                (setq *tsp-data-dirty* T)
                (princ "\n지반 정보가 성공적으로 저장되었습니다. 도면을 작도할 방향을 선택하세요.")
              )
              (princ "\n수정이 취소되었습니다.")
            )
            ;; 루프 계속 유지 (다시 L/R/S 질문으로 돌아감)
          )
          (progn
            ;; L 또는 R을 선택하면 루프를 종료하고 작도 단계로 넘어감
            (setq loop-choice nil)
          )
        )
      )
    )
  )

  ;; 작도 진행 (side가 설정되어 있고 S가 아닌 경우)
  (if (and side (/= side "S"))
    (progn
      (setq start-pt (vl-catch-all-apply 'getpoint (list "\n지반선 기준점 지정: ")))
      (if (vl-catch-all-error-p start-pt)
        (progn (setq start-pt nil) (setq *tsp-cancel-flag* T))
      )
      (if start-pt
        (progn
          ;; UCS -> WCS 변환
          (setq pt1 (trans start-pt 1 0))
          (if (= side "L")
            (setq end-pt (polar start-pt pi 30000.0))
            (setq end-pt (polar start-pt 0.0 30000.0))
          )
          (setq layer-name "_지반선")
          (create-layer-if-not-exists layer-name "8")
          (setq ltype-name "DASHED")
          (if (not (tblsearch "LTYPE" ltype-name))
            (vl-catch-all-apply 'vla-load (list (vla-get-linetypes (vla-get-activedocument (vlax-get-acad-object))) ltype-name (if (= (getvar "MEASUREMENT") 0) "acad.lin" "acadiso.lin")))
          )
          (setq pt2 (trans end-pt 1 0))
          (entmake (list '(0 . "LWPOLYLINE") '(100 . "AcDbEntity") '(100 . "AcDbPolyline") (cons 8 layer-name) (cons 62 8) (cons 6 ltype-name) (cons 48 (if (= (getvar "MEASUREMENT") 0) 1000.0 40.0)) '(90 . 2) '(70 . 0) (cons 10 (list (car pt1) (cadr pt1))) (cons 10 (list (car pt2) (cadr pt2)))))
          
          ;; 주상도 작도 호출
          (draw-soil-column pt2 side)
          
          ;;;; 벽체 타입에 따른 단면도 작도 함수 분기 처리
          (if (equal *tsp-wall-type* "CIP")
            (progn
              (setq cip-h-spec (nth (atoi (if *tsp-cip-hpile-idx* *tsp-cip-hpile-idx* "2")) *tsp-std-wall-list*))
              (setq *tsp-h-pile-size* (parse-h-spec cip-h-spec))
              (setq *tsp-cip-dia* (atof (if (type *tsp-cip-dia*) *tsp-cip-dia* "500")))
              ;; [통합 깊이 변수로 교체] CIP 단면 작도 호출
              (draw-section-cip pt1 side *tsp-max-depth* *tsp-embed-depth* *tsp-support-list*)
            )
            (progn
              (if (= *tsp-hpile-spec* "User-defined")
                (setq h-spec-list *tsp-hpile-custom*)
                (setq h-spec-list (parse-h-spec *tsp-hpile-spec*))
              )
              (setq h (nth 0 h-spec-list) b (nth 1 h-spec-list) tw (nth 2 h-spec-list) tf (nth 3 h-spec-list))
              ;; [통합 깊이 변수로 교체] H-Pile+토류판 단면 작도 호출
              (draw-section-hpile pt1 side h b tw tf *tsp-max-depth* *tsp-embed-depth*)
            )
          )
          (setq draw-success T)
        )
      )
    )
  )
  draw-success
)


;;; ==========================================================================
;;; [SECTION 5] 평면도 작도 로직 (Plan View Logic)
;;; ==========================================================================


;;;;==========================================================================
;;;; defun create-wale-offsets : 각 세그먼트 데이터에 맞춰 띠장(Wale)생성 (사전 검사 동기화 및 마감 완벽 적용)
;;;;==========================================================================
(defun create-wale-offsets (boundary-ent boundary-orient / seg-idx max-idx seg-data is-def v-start v-end v-angle wale-spec h b tw tf wale-offset-sign offset-dir next-idx next-data next-def next-start next-angle prev-idx prev-data prev-def prev-end prev-angle diff-start diff-end int-angle-start int-angle-end is-butt-start is-0-start is-butt-end is-0-end cut-start-p1 cut-start-p2 cut-end-p1 cut-end-p2 p1 p2 p-outer-s p-outer-e p-of-s p-of-e p-if-s p-if-e p-inner-s p-inner-e p-inner-corner prev-offset-dir prev-wale-spec prev-wale-vals h-prev limit-angle upg-s-vals u-h-s u-tf-s L-start upg-e-vals u-h-e u-tf-e L-end seg-length eff-h-start eff-h-end h-prev-base eff-h-prev next-wale-spec next-wale-vals h-next-base eff-h-next next-offset-dir p-splice1 p-splice2 splice1-cut-p1 splice1-cut-p2 splice2-cut-p1 splice2-cut-p2 res-start res-base res-end base-start-cut base-start-cut-p2 base-end-cut base-end-cut-p2 get-corner-upg-vals get-corner-splice-length draw-wale-subsegment make-wale-lw wale-vals is-upgraded-any ctc-mm max-u-h max-u-tf wall-spec hp-b cip-dia-val cip-overlap-val cip-mode cip-base-ctc interval-idx cip-interval wall-type true-h-list true-tf-list t-idx t-data t-h t-tf t-spec t-vals t-upg-s t-next-idx t-upg-e t-L-start t-L-end t-wall-type t-ctc t-len corner-s-h corner-e-h p-splice1-upg p-splice1-base p-splice2-upg p-splice2-base splice1-upg-cut-p1 splice1-upg-cut-p2 splice1-base-cut-p1 splice1-base-cut-p2 splice2-upg-cut-p1 splice2-upg-cut-p2 splice2-base-cut-p1 splice2-base-cut-p2 cip-h-idx wall-vals)


;;;;==========================================================================
;;;; defun make-wale-lw : [보조 1] LWPOLYLINE 강제 생성
;;;;==========================================================================
  (defun make-wale-lw (p1 p2 layer color)
    (entmake (list '(0 . "LWPOLYLINE") '(100 . "AcDbEntity") '(100 . "AcDbPolyline")
                   (cons 8 layer) (cons 62 color) '(90 . 2) '(70 . 0)
                   (list 10 (car p1) (cadr p1)) (list 10 (car p2) (cadr p2))))
  )


;;;;==========================================================================
;;;; defun get-corner-upg-vals : [보조 2] 코너의 상향(Upgrade) 띠장 데이터 추출
;;;;==========================================================================
  (defun get-corner-upg-vals (corner-idx / c-seg c-upg)
    (if (and (>= corner-idx 0) (< corner-idx (length *segment-list*)))
      (progn
        (setq c-seg (nth corner-idx *segment-list*))
        (setq c-upg (cdr (assoc 'UPGRADE-WALE c-seg)))
        (if (and c-upg (= (car c-upg) "Y"))
          (parse-h-spec (cadr c-upg))
          nil
        )
      )
      nil
    )
  )
  ;; [보조 3] 코너의 보강 띠장 설치 길이(Splice Length) 자동 계산
;;;;==========================================================================
;;;; defun get-corner-splice-length : 외부 H-Pile 탐색 및 초단구간 전체 상향 처리 로직 적용
;;;;==========================================================================
(defun get-corner-splice-length (corner-idx v-start v-angle / c-seg c-brace max-l b-dist b-h min-limit d-dist perp-dist best-d best-pt wall-spec wall-vals hp-b far-edge wall-type cip-h-idx seg-len spec-str brace-edge)
  (if (and (>= corner-idx 0) (< corner-idx (length *segment-list*)))
    (progn
      (setq c-seg (nth corner-idx *segment-list*))
      (setq seg-len (cdr (assoc 'LENGTH c-seg)))
      
      (setq wall-type (cdr (assoc 'WALL-TYPE c-seg)))
      (if (= wall-type "CIP")
        (progn
          (setq cip-h-idx (atoi (cdr (assoc 'CIP-HPILE-IDX c-seg))))
          (setq wall-vals (parse-h-spec (nth cip-h-idx *tsp-std-wall-list*)))
        )
        (progn
          (setq wall-spec (cdr (assoc 'WALL-SPEC c-seg)))
          (if (= wall-spec "User-defined")
            (setq wall-vals (cdr (assoc 'WALL-CUSTOM c-seg)))
            (setq wall-vals (parse-h-spec wall-spec))
          )
        )
      )
      (if (null wall-vals) (setq wall-vals '(300 300 10 15)))
      (setq hp-b (nth 1 wall-vals))
      
      (setq c-brace (cdr (assoc 'CORNER-BRACE c-seg)))
      (setq max-l 0.0)
      (if (and c-brace (= (car c-brace) "Y") (cadr c-brace))
        (foreach b-row (cadr c-brace)
          (setq b-dist (* (nth 2 b-row) 1000.0))
          (setq b-h (nth 0 (cadr b-row)))
          (setq spec-str (nth 0 b-row))
          
          ;; 맞버팀대(2H) 여부에 따른 끝단 거리 계산 분기
          (setq brace-edge
            (if (wcmatch (strcase spec-str) "2H*")
              (* b-h 1.5) ; 2H: 이격거리 반폭(0.5H) + 바깥부재폭(1.0H) = 1.5H
              (/ b-h 2.0) ; 일반 H: 중심 반폭 = 0.5H
            )
          )
          
          (if (> (+ b-dist brace-edge) max-l)
            (setq max-l (+ b-dist brace-edge))
          )
        )
      )
      (setq min-limit (if (> max-l 0) (+ max-l 150.0) 0.0))
      
      (if (> min-limit 0.0)
        (progn
          (setq best-d 1e99 best-pt nil)
          (if *tsp-hpile-points*
            (foreach p *tsp-hpile-points*
              (setq d-dist (+ (* (- (car p) (car v-start)) (cos v-angle)) 
                              (* (- (cadr p) (cadr v-start)) (sin v-angle))))
              (setq far-edge (+ d-dist (/ hp-b 2.0)))
              (setq perp-dist (abs (+ (* (- (car p) (car v-start)) (- (sin v-angle))) 
                                      (* (- (cadr p) (cadr v-start)) (cos v-angle)))))
              
              (if (and (> far-edge min-limit) (< perp-dist 500.0) (> d-dist 0.0))
                (if (< d-dist best-d)
                  (setq best-d d-dist best-pt p)
                )
              )
            )
          )
          (if (< best-d 1e90) best-d seg-len)
        )
        0.0
      )
    )
    0.0
  )
)

;;;;==========================================================================
;;;; defun draw-wale-subsegment : [보조 4] 지정된 도막(Sub-segment)의 띠장 라인 4줄 작도
;;;;==========================================================================
  (defun draw-wale-subsegment (p-start p-end cut-s-p1 cut-s-p2 cut-e-p1 cut-e-p2 sub-h sub-tf / p1_outer p2_outer p_outer_s p_outer_e p1_of p2_of p_of_s p_of_e p1_if p2_if p_if_s p_if_e p1_inner p2_inner p_inner_s p_inner_e)
    (if (> (distance p-start p-end) 0.01)
      (progn
        (setq p1_outer (polar p-start offset-dir 0))
        (setq p2_outer (polar p-end offset-dir 0))
        (setq p_outer_s (tsp-get-intersection-point p1_outer p2_outer cut-s-p1 cut-s-p2))
        (setq p_outer_e (tsp-get-intersection-point p1_outer p2_outer cut-e-p1 cut-e-p2))
        (setq p1_of (polar p-start offset-dir sub-tf))
        (setq p2_of (polar p-end offset-dir sub-tf))
        (setq p_of_s (tsp-get-intersection-point p1_of p2_of cut-s-p1 cut-s-p2))
        (setq p_of_e (tsp-get-intersection-point p1_of p2_of cut-e-p1 cut-e-p2))
        (setq p1_if (polar p-start offset-dir (- sub-h sub-tf)))
        (setq p2_if (polar p-end offset-dir (- sub-h sub-tf)))
        (setq p_if_s (tsp-get-intersection-point p1_if p2_if cut-s-p1 cut-s-p2))
        (setq p_if_e (tsp-get-intersection-point p1_if p2_if cut-e-p1 cut-e-p2))
        (setq p1_inner (polar p-start offset-dir sub-h))
        (setq p2_inner (polar p-end offset-dir sub-h))
        (setq p_inner_s (tsp-get-intersection-point p1_inner p2_inner cut-s-p1 cut-s-p2))
        (setq p_inner_e (tsp-get-intersection-point p1_inner p2_inner cut-e-p1 cut-e-p2))
        (if (null p_outer_s) (setq p_outer_s p1_outer))
        (if (null p_outer_e) (setq p_outer_e p2_outer))
        (if (null p_inner_s) (setq p_inner_s p1_inner))
        (if (null p_inner_e) (setq p_inner_e p2_inner))
        (if (null p_of_s) (setq p_of_s p1_of))
        (if (null p_of_e) (setq p_of_e p2_of))
        (if (null p_if_s) (setq p_if_s p1_if))
        (if (null p_if_e) (setq p_if_e p2_if))
        (make-wale-lw p_outer_s p_outer_e "_띠장(wale)" 3)
        (make-wale-lw p_of_s p_of_e "_띠장(wale)" 1)
        (make-wale-lw p_if_s p_if_e "_띠장(wale)" 1)
        (make-wale-lw p_inner_s p_inner_e "_띠장(wale)" 3)
        (list p_outer_s p_inner_s p_outer_e p_inner_e)
      )
      nil
    )
  )

  ;; 1. 레이어 설정 및 초기화
  (create-layer-if-not-exists "_띠장(wale)" "3")
  (setq wale-offset-sign boundary-orient)
  (setq max-idx (length *segment-list*))
  (setq is-upgraded-any nil)
  (princ "\n[작도] 띠장(Wale) 작도 처리 시작...")

  ;; --- [사전 검사 (Pre-Pass)] ---
  ;; 전체 세그먼트의 '최종 베이스 규격(True H, TF)'을 미리 계산하여 이웃 간 절단면 기하학 불일치 원천 차단
  (setq true-h-list '() true-tf-list '())
  (setq t-idx 0)
  (while (< t-idx max-idx)
    (setq t-data (nth t-idx *segment-list*))
    (setq t-h 300 t-tf 15)
    (if (cdr (assoc 'IS-DEFINED t-data))
      (progn
        (setq t-spec (cdr (assoc 'WALE-SPEC t-data)))
        (setq t-vals (if (= t-spec "User-defined") (cdr (assoc 'WALE-CUSTOM t-data)) (parse-h-spec t-spec)))
        (if t-vals (setq t-h (nth 0 t-vals) t-tf (nth 3 t-vals)))
        
        (setq t-upg-s (get-corner-upg-vals t-idx))
        (setq t-next-idx (if (is-closed-polyline boundary-ent) (rem (1+ t-idx) max-idx) (1+ t-idx)))
        (setq t-upg-e (get-corner-upg-vals t-next-idx))
        
        (setq t-L-start (if t-upg-s (get-corner-splice-length t-idx (cdr (assoc 'V-START t-data)) (cdr (assoc 'ANGLE t-data))) 0.0))
        (setq t-L-end (if t-upg-e (get-corner-splice-length t-next-idx (cdr (assoc 'V-END t-data)) (+ (cdr (assoc 'ANGLE t-data)) pi)) 0.0))
        
        (setq t-wall-type (cdr (assoc 'WALL-TYPE t-data)))
        (if (= t-wall-type "CIP")
          (progn
            (setq cip-dia-val (atof (cdr (assoc 'CIP-DIA t-data))))
            (setq cip-overlap-val (atof (cdr (assoc 'CIP-OVERLAP t-data))))
            (setq cip-mode (cdr (assoc 'CIP-MODE-IDX t-data)))
            (setq cip-base-ctc (if (= cip-mode "0") cip-dia-val (- cip-dia-val cip-overlap-val)))
            (setq interval-idx (cdr (assoc 'CIP-INTERVAL-IDX t-data)))
            (setq cip-interval (cond ((= interval-idx "1") 2.0) ((= interval-idx "2") 3.0) (t 1.0)))
            (setq t-ctc (* cip-base-ctc cip-interval))
          )
          (setq t-ctc (* (if (cdr (assoc 'CTC t-data)) (cdr (assoc 'CTC t-data)) 2.0) 1000.0))
        )
        
        (setq t-len (cdr (assoc 'LENGTH t-data)))
        ;; CTC 기준 전체 상향 판단
        (if (and (or (> t-L-start 0.0) (> t-L-end 0.0)) (< (- t-len (+ t-L-start t-L-end)) (* t-ctc 1.5)))
          (progn
            (if t-upg-s (if (> (nth 0 t-upg-s) t-h) (setq t-h (nth 0 t-upg-s) t-tf (nth 3 t-upg-s))))
            (if t-upg-e (if (> (nth 0 t-upg-e) t-h) (setq t-h (nth 0 t-upg-e) t-tf (nth 3 t-upg-e))))
            (setq is-upgraded-any T)
          )
        )
      )
    )
    (setq true-h-list (append true-h-list (list t-h)))
    (setq true-tf-list (append true-tf-list (list t-tf)))
    (setq t-idx (1+ t-idx))
  )
  ;; ------------------------------------------

  ;; 2. 메인 작도: 전체 세그먼트 순회
  (setq seg-idx 0)
  (while (< seg-idx max-idx)
    (setq seg-data (nth seg-idx *segment-list*))
    (setq is-def (cdr (assoc 'IS-DEFINED seg-data)))
    (if is-def
      (progn
        ;; [STEP 1] 현재 세그먼트 기본 파싱
        (setq v-start (cdr (assoc 'V-START seg-data)))
        (setq v-end (cdr (assoc 'V-END seg-data)))
        (setq v-angle (cdr (assoc 'ANGLE seg-data)))
        (setq seg-length (distance v-start v-end))
        (setq offset-dir (+ v-angle (* (/ pi 2.0) wale-offset-sign)))
        
        (setq wall-type (cdr (assoc 'WALL-TYPE seg-data)))
        (if (= wall-type "CIP")
          (progn
            (setq cip-h-idx (atoi (cdr (assoc 'CIP-HPILE-IDX seg-data))))
            (setq wall-vals (parse-h-spec (nth cip-h-idx *tsp-std-wall-list*)))
          )
          (progn
            (setq wall-spec (cdr (assoc 'WALL-SPEC seg-data)))
            (if (= wall-spec "User-defined")
              (setq wall-vals (cdr (assoc 'WALL-CUSTOM seg-data)))
              (setq wall-vals (parse-h-spec wall-spec))
            )
          )
        )
        (if (null wall-vals) (setq wall-vals '(300 300 10 15)))
        (setq hp-b (nth 1 wall-vals))
        
        ;; Pre-Pass에서 도출된 현재 구간의 규격(True H) 적용
        (setq h (nth seg-idx true-h-list) tf (nth seg-idx true-tf-list))
        
        ;; [STEP 2] 동기화된 인접 규격 및 보강 도막(Splice) 계산
        (setq next-idx (if (is-closed-polyline boundary-ent) (rem (1+ seg-idx) max-idx) (1+ seg-idx)))
        (setq prev-idx (if (is-closed-polyline boundary-ent) (if (= seg-idx 0) (1- max-idx) (1- seg-idx)) (1- seg-idx)))
        
        ;; 열린 경계선의 경우 시작/끝점에서 인덱스가 -1 또는 max-idx를 벗어나 에러가 발생하는 것을 방지하는 안전 검사 추가
        (setq next-data (if (and (>= next-idx 0) (< next-idx max-idx)) (nth next-idx *segment-list*) nil))
        (setq prev-data (if (and (>= prev-idx 0) (< prev-idx max-idx)) (nth prev-idx *segment-list*) nil))
        
        (setq next-def (if next-data (cdr (assoc 'IS-DEFINED next-data)) nil))
        (setq prev-def (if prev-data (cdr (assoc 'IS-DEFINED prev-data)) nil))
        
        (setq next-start (if next-def (cdr (assoc 'V-START next-data)) nil))
        (setq next-angle (if next-def (cdr (assoc 'ANGLE next-data)) nil))
        (setq prev-end (if prev-def (cdr (assoc 'V-END prev-data)) nil))
        (setq prev-angle (if prev-def (cdr (assoc 'ANGLE prev-data)) nil))

        ;; 이웃 세그먼트의 True H 추출
        (setq h-prev-base (if prev-def (nth prev-idx true-h-list) h))
        (setq h-next-base (if next-def (nth next-idx true-h-list) h))
        
        ;; 모서리에 사용자가 명시한 보강재 규격 추출
        (setq upg-s-vals (get-corner-upg-vals seg-idx))
        (setq corner-s-h (if upg-s-vals (nth 0 upg-s-vals) 0))
        (setq upg-e-vals (get-corner-upg-vals next-idx))
        (setq corner-e-h (if upg-e-vals (nth 0 upg-e-vals) 0))
        
        ;; 절단면(Cutting Plane)의 최종 폭은 만나는 두 구간과 모서리 규격 중 '최대값'
        (setq eff-h-start (max h h-prev-base corner-s-h))
        (setq eff-h-prev eff-h-start)
        
        (setq eff-h-end (max h h-next-base corner-e-h))
        (setq eff-h-next eff-h-end)
        
        ;; 보강 띠장 도막(Splice) 생성 여부 결정
        ;; 내 구간 최종 베이스 폭(h)보다 모서리 필요 폭(eff-h)이 더 클 때만 돌출 도막 생성
        (if (> eff-h-start h)
          (progn
            (setq u-h-s eff-h-start)
            (setq u-tf-s (if (and upg-s-vals (= corner-s-h eff-h-start)) (nth 3 upg-s-vals) tf))
            (setq L-start (get-corner-splice-length seg-idx v-start v-angle))
          )
          (setq L-start 0.0 u-h-s nil)
        )
        
        (if (> eff-h-end h)
          (progn
            (setq u-h-e eff-h-end)
            (setq u-tf-e (if (and upg-e-vals (= corner-e-h eff-h-end)) (nth 3 upg-e-vals) tf))
            (setq L-end (get-corner-splice-length next-idx v-end (+ v-angle pi)))
          )
          (setq L-end 0.0 u-h-e nil)
        )
        
        (if (or (> L-start 0.0) (> L-end 0.0))
          (setq is-upgraded-any T)
        )

        (if (> (+ L-start L-end) seg-length)
          (progn
            (setq L-start (min L-start (/ seg-length 2.0)))
            (setq L-end (min L-end (/ seg-length 2.0)))
          )
        )

        ;; [STEP 3] 시작점 절단면 계산 (eff-h 기준)
        (setq is-butt-start nil is-0-start nil)
        (setq limit-angle (* 120.0 (/ pi 180.0)))
        (if prev-def
          (progn
            (setq diff-start (abs (- v-angle prev-angle)))
            (while (> diff-start pi) (setq diff-start (abs (- diff-start (* 2.0 pi)))))
            (setq int-angle-start (- pi diff-start))
            (if (< diff-start 0.01) (setq is-0-start T))
            (if (and (>= diff-start 0.01) (<= int-angle-start (+ limit-angle 0.01))) (setq is-butt-start T))
          )
        )
        (cond
          ((or (not prev-def) is-0-start)
           (setq cut-start-p1 v-start)
           (setq cut-start-p2 (polar v-start offset-dir 100.0))
          )
          (is-butt-start
           (setq prev-offset-dir (+ prev-angle (* (/ pi 2.0) wale-offset-sign)))
           (setq cut-start-p1 (polar v-start prev-offset-dir eff-h-prev))
           (setq cut-start-p2 (polar cut-start-p1 prev-angle 100.0))
          )
          (t
           (setq prev-offset-dir (+ prev-angle (* (/ pi 2.0) wale-offset-sign)))
           (setq p-inner-corner (tsp-get-intersection-point
                                  (polar v-start offset-dir eff-h-start) (polar v-end offset-dir eff-h-start)
                                  (polar prev-end prev-offset-dir eff-h-prev)
                                  (polar (cdr (assoc 'V-START prev-data)) prev-offset-dir eff-h-prev)))
           (if (null p-inner-corner) (setq p-inner-corner (polar v-start offset-dir eff-h-start)))
           (setq cut-start-p1 v-start)
           (setq cut-start-p2 p-inner-corner)
          )
        )
        ;; [STEP 4] 끝점 절단면 계산 (eff-h 기준)
        (setq is-butt-end nil is-0-end nil)
        (if next-def
          (progn
            (setq diff-end (abs (- next-angle v-angle)))
            (while (> diff-end pi) (setq diff-end (abs (- diff-end (* 2.0 pi)))))
            (setq int-angle-end (- pi diff-end))
            (if (< diff-end 0.01) (setq is-0-end T))
            (if (and (>= diff-end 0.01) (<= int-angle-end (+ limit-angle 0.01))) (setq is-butt-end T))
          )
        )
        (cond
          ((or (not next-def) is-0-end)
           (setq cut-end-p1 v-end)
           (setq cut-end-p2 (polar v-end offset-dir 100.0))
          )
          (is-butt-end
           (setq cut-end-p1 v-end)
           (setq cut-end-p2 (polar v-end next-angle 100.0))
          )
          (t
           (setq next-offset-dir (+ next-angle (* (/ pi 2.0) wale-offset-sign)))
           (setq p-inner-corner (tsp-get-intersection-point
                                  (polar v-start offset-dir eff-h-end) (polar v-end offset-dir eff-h-end)
                                  (polar next-start next-offset-dir eff-h-next)
                                  (polar (cdr (assoc 'V-END next-data)) next-offset-dir eff-h-next)))
           (if (null p-inner-corner) (setq p-inner-corner (polar v-end offset-dir eff-h-end)))
           (setq cut-end-p1 v-end)
           (setq cut-end-p2 p-inner-corner)
          )
        )
        ;; [STEP 5] Splice 절단면 계산 (직각 절단 및 동적 플랜지 너비 오버랩 적용)
        (if (> L-start 0.0)
          (progn
            (setq p-splice1-upg (polar v-start v-angle (+ L-start (/ hp-b 2.0))))
            (setq p-splice1-base (polar v-start v-angle (- L-start (/ hp-b 2.0))))
          )
          (progn
            (setq p-splice1-upg v-start)
            (setq p-splice1-base v-start)
          )
        )
        (if (> L-end 0.0)
          (progn
            (setq p-splice2-upg (polar v-end (+ v-angle pi) (+ L-end (/ hp-b 2.0))))
            (setq p-splice2-base (polar v-end (+ v-angle pi) (- L-end (/ hp-b 2.0))))
          )
          (progn
            (setq p-splice2-upg v-end)
            (setq p-splice2-base v-end)
          )
        )

        (setq splice1-upg-cut-p1 p-splice1-upg)
        (setq splice1-upg-cut-p2 (polar p-splice1-upg offset-dir 100.0))
        (setq splice1-base-cut-p1 p-splice1-base)
        (setq splice1-base-cut-p2 (polar p-splice1-base offset-dir 100.0))

        (setq splice2-upg-cut-p1 p-splice2-upg)
        (setq splice2-upg-cut-p2 (polar p-splice2-upg offset-dir 100.0))
        (setq splice2-base-cut-p1 p-splice2-base)
        (setq splice2-base-cut-p2 (polar p-splice2-base offset-dir 100.0))

        ;; [STEP 6] 3도막(Sub-segments) 작도
        (setq res-start nil res-base nil res-end nil)
        
        ;; 6.1 Start Upgrade Wale (상향 띠장: 플랜지 너비의 절반만큼 더 연장)
        (if (> L-start 0.0)
          (setq res-start (draw-wale-subsegment v-start p-splice1-upg cut-start-p1 cut-start-p2 splice1-upg-cut-p1 splice1-upg-cut-p2 u-h-s u-tf-s))
        )
        
        ;; 6.2 Base Wale (일반 띠장: 플랜지 너비의 절반만큼 축소하여 시작/마감)
        (setq base-start-cut (if (> L-start 0.0) splice1-base-cut-p1 cut-start-p1))
        (setq base-start-cut-p2 (if (> L-start 0.0) splice1-base-cut-p2 cut-start-p2))
        (setq base-end-cut (if (> L-end 0.0) splice2-base-cut-p1 cut-end-p1))
        (setq base-end-cut-p2 (if (> L-end 0.0) splice2-base-cut-p2 cut-end-p2))
        
        (setq res-base (draw-wale-subsegment (if (> L-start 0.0) p-splice1-base v-start)
                                             (if (> L-end 0.0) p-splice2-base v-end)
                                             base-start-cut base-start-cut-p2
                                             base-end-cut base-end-cut-p2
                                             h tf))
                                             
        ;; 6.3 End Upgrade Wale (상향 띠장: 플랜지 너비의 절반만큼 더 연장)
        (if (> L-end 0.0)
          (setq res-end (draw-wale-subsegment p-splice2-upg v-end splice2-upg-cut-p1 splice2-upg-cut-p2 cut-end-p1 cut-end-p2 u-h-e u-tf-e))
        )
        ;; [STEP 7] 모든 절단면 마감 및 단차 연결 완벽 적용 (Capping)
        ;; 7.1 코너부 끝단 (Extreme Ends)
        (if res-start
          (make-wale-lw (nth 0 res-start) (nth 1 res-start) "_띠장(wale)" 3)
          (if res-base (make-wale-lw (nth 0 res-base) (nth 1 res-base) "_띠장(wale)" 3))
        )
        (if res-end
          (make-wale-lw (nth 2 res-end) (nth 3 res-end) "_띠장(wale)" 3)
          (if res-base (make-wale-lw (nth 2 res-base) (nth 3 res-base) "_띠장(wale)" 3))
        )
        ;; 7.2 Splice 부분 절단면 및 단차 완전 마감 (Cut Ends Capping)
        (if res-start
          (make-wale-lw (nth 2 res-start) (nth 3 res-start) "_띠장(wale)" 3)
        )
        (if res-base
          (progn
            (if res-start (make-wale-lw (nth 0 res-base) (nth 1 res-base) "_띠장(wale)" 3))
            (if res-end   (make-wale-lw (nth 2 res-base) (nth 3 res-base) "_띠장(wale)" 3))
          )
        )
        (if res-end
          (make-wale-lw (nth 0 res-end) (nth 1 res-end) "_띠장(wale)" 3)
        )
      ) ; end progn (if is-def)
    )
    (setq seg-idx (1+ seg-idx))
  )
  (if is-upgraded-any
    (princ "\n띠장 상향 완료.")
    (princ "\n띠장 작도 완료.")
  )
  (princ)
)


;;;;==========================================================================
;;;; defun calculate-corner-params : 코너 부위에서 H-Pile의 회전각 및 삽입 위치 계산
;;;;==========================================================================
(defun calculate-corner-params (vertex prev-vertex next-vertex h b timber-offset boundary-orient / is-convex half-b angle1 angle2 prev-dir next-dir wale-corner wale-corner-angle hpile-rotation offset-dir insert-point half-angle offset-dist)
  (setq half-b (/ b 2.0))
  ;; 1. 코너 방향 판별 (볼록/오목)
  (setq is-convex (is-corner-convex prev-vertex vertex next-vertex boundary-orient))
  ;; 2. 각도 계산
  (setq angle1 (angle prev-vertex vertex))
  (setq angle2 (angle vertex next-vertex))
  ;; 방향 벡터 설정
  (setq prev-dir (+ angle1 (* boundary-orient (/ pi 2.0))))
  (setq next-dir (+ angle2 (* boundary-orient (/ pi 2.0))))
  ;; 3. 이등분선(Wale Corner) 위치 및 각도 계산
  (setq wale-corner (list
    (/ (+ (car (polar vertex prev-dir timber-offset)) (car (polar vertex next-dir timber-offset))) 2.0)
    (/ (+ (cadr (polar vertex prev-dir timber-offset)) (cadr (polar vertex next-dir timber-offset))) 2.0)
    0.0))
  (setq wale-corner-angle (angle vertex wale-corner))
  ;; 4. H-Pile 회전 각도 결정 (이등분선 + 90도)
  (setq hpile-rotation (+ wale-corner-angle (/ pi 2.0)))
  ;; 5. 삽입점(Insert Point) 결정
  (if is-convex
    (progn
      ;; [볼록한 경우] - 정점에 배치
      (setq insert-point vertex)
    )
    (progn
      ;; [오목한 경우] - 사용자 지정 공식 적용
      ;; 공식: l = B/2 * tan(90-a)
      ;; 여기서 a는 half-angle
      ;; a (Half Angle) 계산
      (setq half-angle (abs (- angle2 wale-corner-angle)))
      ;; 각도 정규화 (PI보다 크면 반대쪽 각도)
      (if (> half-angle pi) (setq half-angle (- (* 2.0 pi) half-angle)))
      ;; 0으로 나누기 방지 (매우 뾰족한 경우 안전장치)
      (if (< half-angle 0.001) (setq half-angle 0.001))
      ;; 거리 l 계산: tan(90-a) = cot(a) = cos(a)/sin(a)
      (setq offset-dist (* half-b (/ (cos half-angle) (sin half-angle))))
      ;; 방향: 이등분선 방향으로 이격
      (setq offset-dir wale-corner-angle)
      ;; 최종 좌표 계산
      (setq insert-point (polar vertex offset-dir offset-dist))
    )
  )
  ;; 결과 반환
  (list insert-point hpile-rotation is-convex)
)


;;;;==========================================================================
;;;; defun get-hpile-limit-offset : H-Pile 배치 시 플랜지 간섭을 피하기 위한 한계 오프셋 계산
;;;;==========================================================================
(defun get-hpile-limit-offset (hpile-pt h b tf rotation seg-origin seg-angle is-start is-convex / half-h half-b corners pt dx dy proj-dist best-dist wx wy)
  (setq half-h (/ h 2.0) half-b (/ b 2.0))
  (if is-convex
    (setq corners (list
      (list (- half-b) 0)
      (list half-b 0)
      (list half-b h)
      (list (- half-b) h)
    ))
    (setq corners (list
      (list (- half-b) tf)
      (list half-b tf)
    ))
  )
  (setq best-dist (if is-start -1e99 1e99))
  (foreach pt corners
    (setq wx (+ (car hpile-pt) (- (* (car pt) (cos rotation)) (* (cadr pt) (sin rotation)))))
    (setq wy (+ (cadr hpile-pt) (+ (* (car pt) (sin rotation)) (* (cadr pt) (cos rotation)))))
    (setq dx (- wx (car seg-origin)))
    (setq dy (- wy (cadr seg-origin)))
    (setq proj-dist (+ (* dx (cos seg-angle)) (* dy (sin seg-angle))))
    (if is-start
      (if (> proj-dist best-dist) (setq best-dist proj-dist))
      (if (< proj-dist best-dist) (setq best-dist proj-dist))
    )
  )
  best-dist
)


;;;;==========================================================================
;;;; defun create-hpile-section : H-Pile 폴리라인 형상 생성
;;;;==========================================================================
(defun create-hpile-section (insert-pt h b tw tf layer-name / pts)
  ;; 공통 함수를 통해 좌표 리스트 획득 (insert-pt가 이미 중심점)
  (setq pts (calc-hpile-vertices insert-pt h b tw tf))
  (entmake (list '(0 . "LWPOLYLINE") '(100 . "AcDbEntity") '(100 . "AcDbPolyline")
    (cons 8 layer-name) (cons 62 3) '(90 . 20) '(70 . 1)
    (cons 10 (nth 0 pts))  (cons 10 (nth 1 pts))
    (cons 10 (nth 2 pts))  (cons 42 0.4142135623730951) (cons 10 (nth 3 pts))
    (cons 10 (nth 4 pts))  (cons 42 0.4142135623730951) (cons 10 (nth 5 pts))
    (cons 10 (nth 6 pts))  (cons 10 (nth 7 pts))
    (cons 10 (nth 8 pts))  (cons 10 (nth 9 pts))
    (cons 10 (nth 10 pts)) (cons 42 0.4142135623730951) (cons 10 (nth 11 pts))
    (cons 10 (nth 12 pts)) (cons 42 0.4142135623730951) (cons 10 (nth 13 pts))
    (cons 10 (nth 14 pts)) (cons 10 (nth 15 pts))))
  (entlast)
)


;;;;==========================================================================
;;;; defun create-hpile-section-block : H-Pile 단면 형상을 블록으로 정의
;;;;==========================================================================
(defun create-hpile-section-block (h b tw tf / hpile-ent point-ent block-name layer-name old-ucs old-osnap half-h)
  (setq block-name (strcat "_HPILE(" (itoa h) "x" (itoa b) "x" (itoa tw) "x" (itoa tf) ")"))
  (setq layer-name (strcat "_H-Pile_" (itoa h) "x" (itoa b) "x" (itoa tw) "-" (itoa tf)))
  (create-layer-if-not-exists layer-name "3")
  (create-layer-if-not-exists "_측면말뚝" "3")
  (if (not (tblsearch "BLOCK" block-name))
    (progn
      (setq old-ucs (getvar "UCSNAME") old-osnap (getvar "OSMODE"))
      (command "._UCS" "_W") (setvar "OSMODE" 0)
      ;; 수정된 create-hpile-section 함수를 호출하여 형상을 그립니다.
      (setq hpile-ent (create-hpile-section '(0 0) h b tw tf layer-name))
      (setq half-h (/ h 2.0))
      (entmake (list '(0 . "POINT") '(8 . "_측면말뚝") (cons 10 (list 0.0 (- half-h) 0.0))))
      (setq point-ent (entlast))
      (command "._-BLOCK" block-name (list 0.0 (- half-h) 0.0) hpile-ent point-ent "")
      (if old-ucs (command "._UCS" "_R" old-ucs) (command "._UCS" "_W"))
      (setvar "OSMODE" old-osnap)
    )
  )
  block-name
)


;;;;==========================================================================
;;;; defun create-post-pile-block : 중간말뚝(Post Pile) 블록 정의
;;;;==========================================================================
(defun create-post-pile-block (h b tw tf / hpile-ent point-ent point-ent2 block-name layer-name old-ucs old-osnap half-h half-b ss)
  (setq block-name (strcat "_POST_PILE(" (itoa (fix h)) "x" (itoa (fix b)) "x" (itoa (fix tw)) "x" (itoa (fix tf)) ")"))
  (setq layer-name (strcat "_H-Pile_" (itoa (fix h)) "x" (itoa (fix b)) "x" (itoa (fix tw)) "-" (itoa (fix tf))))
  (create-layer-if-not-exists layer-name "3")
  (create-layer-if-not-exists "_중간말뚝(Post pile)" "3")
  (if (not (tblsearch "BLOCK" block-name))
    (progn
      (setq old-ucs (getvar "UCSNAME") old-osnap (getvar "OSMODE"))
      (command "._UCS" "_W") (setvar "OSMODE" 0)
      (setq hpile-ent (create-hpile-section '(0 0) h b tw tf layer-name))
      (setq half-h (/ h 2.0))
      (setq half-b (/ b 2.0))
      
      (entmake (list '(0 . "POINT") '(8 . "_중간말뚝(Post pile)") (cons 10 (list 0.0 (- half-h) 0.0))))
      (setq point-ent (entlast))
      
      ;; 플랜지 아랫면 왼쪽 모서리에 추가 POINT 생성 (- half-b 적용)
      (entmake (list '(0 . "POINT") '(8 . "_중간말뚝(Post pile)") (cons 10 (list (- half-b) (- half-h) 0.0))))
      (setq point-ent2 (entlast))
      
      ;; 에러 방지를 위해 객체들을 하나의 선택 세트(Selection Set)로 묶음
      (setq ss (ssadd))
      (ssadd hpile-ent ss)
      (ssadd point-ent ss)
      (ssadd point-ent2 ss)
      
      ;; 묶인 선택 세트(ss)를 이용해 블록 생성
      (command "._-BLOCK" block-name (list 0.0 (- half-h) 0.0) ss "")
      (if old-ucs (command "._UCS" "_R" old-ucs) (command "._UCS" "_W"))
      (setvar "OSMODE" old-osnap)
    )
  )
  block-name
)


;;;;==========================================================================
;;;; defun create-timber-panel-object : 평면도 토류판 폴리라인 및 해치 생성
;;;;==========================================================================
(defun create-timber-panel-object (center-pt width height rot-angle / half-width half-height cos-a sin-a pt1 pt2 pt3 pt4 timber-pline hatch-obj sa doc mspace top-left top-right origin-sa)
  (setq half-width (/ width 2.0) half-height (/ height 2.0))
  (setq cos-a (cos rot-angle) sin-a (sin rot-angle))
  (setq pt1 (list (+ (car center-pt) (- (* (- half-width) cos-a) (* (- half-height) sin-a))) (+ (cadr center-pt) (+ (* (- half-width) sin-a) (* (- half-height) cos-a)))))
  (setq pt2 (list (+ (car center-pt) (- (* half-width cos-a) (* (- half-height) sin-a))) (+ (cadr center-pt) (+ (* half-width sin-a) (* (- half-height) cos-a)))))
  (setq pt3 (list (+ (car center-pt) (- (* half-width cos-a) (* half-height sin-a))) (+ (cadr center-pt) (+ (* half-width sin-a) (* half-height cos-a)))))
  (setq pt4 (list (+ (car center-pt) (- (* (- half-width) cos-a) (* half-height sin-a))) (+ (cadr center-pt) (+ (* (- half-width) sin-a) (* half-height cos-a)))))
  (setq top-right pt3)
  (setq top-left pt4)
  (entmake (list '(0 . "LWPOLYLINE") '(100 . "AcDbEntity") '(100 . "AcDbPolyline") '(8 . "_토류판(timber)") '(62 . 1) '(90 . 4) '(70 . 1) (cons 10 pt1) (cons 10 pt2) (cons 10 pt3) (cons 10 pt4)))
  (setq timber-pline (entlast))
  (if timber-pline
    (progn
      (setq doc (vla-get-activedocument (vlax-get-acad-object)))
      (setq mspace (vla-get-modelspace doc))
      (setq hatch-obj (vla-addhatch mspace 1 "ANSI36" :vlax-true))
      (vla-put-patternscale hatch-obj (* 80.0 (get-hatch-scale-factor)))
      (vla-put-patternangle hatch-obj (* 15.0 (/ pi 180.0)))
      (vla-put-layer hatch-obj "_토류판(timber)")
      (vla-put-color hatch-obj 9)
      (setq sa (vlax-make-safearray 9 (cons 0 0)))
      (vlax-safearray-fill sa (list (vlax-ename->vla-object timber-pline)))
      (vla-appendouterloop hatch-obj sa)
      (setq origin-sa (vlax-make-safearray 5 '(0 . 1)))
      (vlax-safearray-fill origin-sa (list (car center-pt) (cadr center-pt)))
      (vla-put-origin hatch-obj origin-sa)
      (vla-evaluate hatch-obj)
    )
  )
  (entmake (list '(0 . "POINT") '(8 . "_토류판(timber)") '(62 . 1) (cons 10 top-left)))
  (entmake (list '(0 . "POINT") '(8 . "_토류판(timber)") '(62 . 1) (cons 10 top-right)))
  (list timber-pline top-left top-right)
)


;;;;==========================================================================
;;;; defun place-hpile-at-corner-simple : 코너 부위에 단일 H-Pile 블록 배치
;;;;==========================================================================
(defun place-hpile-at-corner-simple (vertex angle1 angle2 h b tw tf hpile-block timber-offset boundary-orient prev-vertex next-vertex / hpile-info insert-point hpile-rotation is-convex half-b local-y flange-left flange-right)
  (setq half-b (/ b 2.0))
  (setq hpile-info (calculate-corner-params vertex prev-vertex next-vertex h b timber-offset boundary-orient))
  (setq insert-point (car hpile-info))
  (setq hpile-rotation (cadr hpile-info))
  (setq is-convex (nth 2 hpile-info))
  (entmake (list '(0 . "INSERT") (cons 2 hpile-block) '(8 . "_측면말뚝") (cons 10 insert-point) '(41 . 1.0) '(42 . 1.0) '(43 . 1.0) (cons 50 hpile-rotation)))
  ;; [추가] 생성된 H-Pile 삽입점(플랜지 바닥 중심) 캐싱
  (setq *tsp-hpile-points* (append *tsp-hpile-points* (list insert-point)))
  (setq local-y (if is-convex 0.0 tf))
  (setq flange-left (list
    (+ (car insert-point) (- (* (- half-b) (cos hpile-rotation)) (* local-y (sin hpile-rotation))))
    (+ (cadr insert-point) (+ (* (- half-b) (sin hpile-rotation)) (* local-y (cos hpile-rotation))))
    0.0))
  (setq flange-right (list
    (+ (car insert-point) (- (* half-b (cos hpile-rotation)) (* local-y (sin hpile-rotation))))
    (+ (cadr insert-point) (+ (* half-b (sin hpile-rotation)) (* local-y (cos hpile-rotation))))
    0.0))
  (create-layer-if-not-exists "DEBUG_FLANGE" "2")
  (entmake (list '(0 . "POINT") '(8 . "DEBUG_FLANGE") '(62 . 2) (cons 10 flange-left)))
  (entmake (list '(0 . "POINT") '(8 . "DEBUG_FLANGE") '(62 . 2) (cons 10 flange-right)))
)


;;;;==========================================================================
;;;; defun place-hpile-timber-along-boundary : 평면도 H-Pile/토류판 통합 작도
;;;;==========================================================================
(defun place-hpile-timber-along-boundary (boundary-ent boundary-orient / make-lw-line h b tw tf hpile-values hpile-block timber-width timber-offset corner-gap boundary-data orig-vertices is-closed num-vertices i prev-idx next-idx prev-vertex curr-vertex next-vertex angle1 angle2 angle-diff turn-direction bisector-angle corner-rotation seg-idx max-segments n-verts pt1 pt2 seg-length seg-angle mid-pt ctc-mm outward-normal start-idx start-prev start-next start-vertex end-idx end-prev end-next end-vertex start-hpile-info end-hpile-info start-limit end-limit safe-start safe-end final-width final-center-dist timber-pt timber-pt-offset dist new-pt hpile-rotation timber-result timber-pline top-left top-right edge-gap left-hpile-pt right-hpile-pt left-offset-pt right-offset-pt timber-idx total-timbers d-start piles-A piles-B timbers-A timbers-B count-A count-B use-method-B final-piles final-timbers temp-dist center start-pile-placed end-pile-placed start-pile-pt end-pile-pt start-is-corner end-is-corner range new-start new-end raw-start raw-end valid-timbers potential-start potential-end seg-data is-def current-spec current-ctc prev-seg-idx next-seg-idx prev-spec next-spec prev-vals next-vals h-prev b-prev h-next b-next current-thick target-seg-data theory-count-A theory-count-B h-start b-start h-end b-end tf-start tf-end wale-spec wale-vals wale-h max-anchor-L max-anchor-ang max-anchor-free max-anchor-bond has-anchor cur-free cur-bond cur-ang cur-L proj-free proj-bond pt-base pt-free-end pt-bond-end pt-h1 pt-h2 pt-h3 pt-h4 cos-val proj-prot pt-anchor-start mid-pile-count prev-def next-def next-seg-real-idx cur-brace prev-brace dist-to-start dist-to-end brace-blocked p-brace b-spec b-custom b-dist-m b-dist b-h dir-A dir-B norm-A norm-B pt-A-base pt-B-base pt-A-inner pt-B-inner brace-dir half-w L1-A L1-B L2-A L2-B pA1 pB1 pA2 pB2 wA1 wA2 wB1 wB2 brace-b-rows b-row chk-last-b-row chk-b-custom chk-b-dist chk-b-h chk-margin next-brace idx w-h-prev w-h-next draw-closed-poly vW-A dot-A pBaseExt-A pBaseOth-A isExtA2 p1_foot-A p1_14-A p1-A l2_p2-A p2-A p2_foot-A p2_14-A p3-A p2_end-A p3_end-A brace_A1 brace_A2 brace-dir-B vW-B dot-B pBaseExt-B pBaseOth-B isExtB2 p1_foot-B p1_14-B p1-B l2_p2-B p2-B p2_foot-B p2_14-B p3-B p2_end-B p3_end-B brace_B1 brace_B2 brace_A1_in brace_A2_in brace_B1_in brace_B2_in b-tw half-tw mid_A_in mid_B_in web1_A web1_B web2_A web2_B b-row-idx b-jack jack-side jack-len pt-jack-ins jack-rot in-continuous-chain carry-over-rem angle-tolerance next-is-continuous next-pt1 next-pt2 angle-next ang-diff use-directional pos t-start t-center skip-this-corner)
  ;; [내부 헬퍼] 2D 좌표 변환 및 LWPOLYLINE 강제 생성
;;;;==========================================================================
;;;; defun make-lw-line : 선분 생성 보조
;;;;==========================================================================
  (defun make-lw-line (p1 p2 layer color)
    (entmake (list '(0 . "LWPOLYLINE") '(100 . "AcDbEntity") '(100 . "AcDbPolyline")
                   (cons 8 layer) (cons 62 color) '(90 . 2) '(70 . 0)
                   (list 10 (car p1) (cadr p1)) (list 10 (car p2) (cadr p2))))
  )
  (setq corner-gap 50.0)
  (setq edge-gap 25.0)
  
  ;; (setq *tsp-segment-pile-counts* '())
  (setq is-closed (is-closed-polyline boundary-ent))
  (setq orig-vertices (mapcar '(lambda (item) (cdr (assoc 'V-START item))) *segment-list*))
  (if (not is-closed) (setq orig-vertices (append orig-vertices (list (cdr (assoc 'V-END (last *segment-list*)))))))
  (setq num-vertices (length orig-vertices))
  (setq seg-idx 0 n-verts num-vertices)
  (setq max-segments (if is-closed n-verts (- n-verts 1)))
  (while (< seg-idx max-segments)
    (setq seg-data (nth seg-idx *segment-list*))
    (setq is-def (cdr (assoc 'IS-DEFINED seg-data)))
    (setq mid-pile-count 0)
    ;; [7단계] CIP 세그먼트는 place-hpile-timber에서 건너뜀
    ;; (CIP는 tsp-draw-cip-plan-per-segment에서 별도 처리)
    (if (= (cdr (assoc 'WALL-TYPE seg-data)) "CIP")
      (setq is-def nil)
    )
    (if is-def
      (progn
        (setq current-spec (cdr (assoc 'WALL-SPEC seg-data)))
        (if (= current-spec "User-defined") (setq hpile-values (cdr (assoc 'WALL-CUSTOM seg-data))) (setq hpile-values (parse-h-spec current-spec)))
        (setq h (nth 0 hpile-values) b (nth 1 hpile-values) tw (nth 2 hpile-values) tf (nth 3 hpile-values))
        (setq current-ctc (cdr (assoc 'CTC seg-data)))
        (setq ctc-mm (* current-ctc 1000.0))
        (setq current-thick (cdr (assoc 'TIMBER-THICKNESS seg-data)))
        (if (null current-thick) (setq current-thick 60))
        (setq timber-offset (+ tf (/ current-thick 2.0)))
        (setq timber-width (- (* current-ctc 1000) 50))
        (setq hpile-block (create-hpile-section-block h b tw tf))
        (setq pt1 (nth seg-idx orig-vertices))
        (setq pt2 (nth (if is-closed (rem (+ seg-idx 1) n-verts) (+ seg-idx 1)) orig-vertices))
        (setq seg-length (distance pt1 pt2) seg-angle (angle pt1 pt2))
        (setq mid-pt (list (/ (+ (car pt1) (car pt2)) 2.0) (/ (+ (cadr pt1) (cadr pt2)) 2.0) 0.0))
        (setq outward-normal (+ seg-angle (* boundary-orient (/ pi 2.0))))
        (setq hpile-rotation (+ outward-normal (/ pi 2.0)))
        (setq wale-spec (cdr (assoc 'WALE-SPEC seg-data)))
        (if (= wale-spec "User-defined") (setq wale-vals (cdr (assoc 'WALE-CUSTOM seg-data))) (setq wale-vals (parse-h-spec wale-spec)))
        (if (null wale-vals) (setq wale-vals '(300 300 10 15)))
        (setq wale-h (nth 0 wale-vals))
        (setq max-anchor-L 0.0 max-anchor-ang 0.0 max-anchor-free 0.0 max-anchor-bond 0.0 has-anchor nil)
        (foreach s-item (cdr (assoc 'SUPPORT-LIST seg-data))
          (if (wcmatch (car s-item) "앵커*")
            (progn
              (setq cur-free (nth 5 s-item) cur-bond (nth 6 s-item) cur-ang (nth 4 s-item))
              (setq cur-L (+ cur-free cur-bond))
              (if (> cur-L max-anchor-L) (progn (setq max-anchor-L cur-L max-anchor-ang cur-ang max-anchor-free cur-free max-anchor-bond cur-bond has-anchor T)))
            )
          )
        )
        (setq start-pile-placed nil end-pile-placed nil start-is-corner nil end-is-corner nil)
        (setq start-idx seg-idx end-idx (if is-closed (rem (+ seg-idx 1) n-verts) (+ seg-idx 1)))
        (setq h-start h b-start b tf-start tf)
        (setq prev-idx (if is-closed (if (= start-idx 0) (- n-verts 1) (- start-idx 1)) (- start-idx 1)))
        (setq prev-def (if (>= prev-idx 0) (cdr (assoc 'IS-DEFINED (nth prev-idx *segment-list*))) nil))
        (if prev-def
          (progn
            (setq prev-spec (cdr (assoc 'WALL-SPEC (nth prev-idx *segment-list*))))
            (if (= prev-spec "User-defined") (setq prev-vals (cdr (assoc 'WALL-CUSTOM (nth prev-idx *segment-list*)))) (setq prev-vals (parse-h-spec prev-spec)))
            (setq h-prev (nth 0 prev-vals) b-prev (nth 1 prev-vals))
            (if (or (> h-prev h) (and (= h-prev h) (> b-prev b))) (setq h-start h-prev b-start b-prev tf-start (nth 3 prev-vals)))
          )
        )
        (setq h-end h b-end b tf-end tf)
        (setq next-seg-real-idx (if is-closed (rem (+ seg-idx 1) n-verts) (+ seg-idx 1)))
        (setq next-def (if (< next-seg-real-idx max-segments) (cdr (assoc 'IS-DEFINED (nth next-seg-real-idx *segment-list*))) nil))
        (if next-def
          (progn
             (setq next-spec (cdr (assoc 'WALL-SPEC (nth next-seg-real-idx *segment-list*))))
             (if (= next-spec "User-defined") (setq next-vals (cdr (assoc 'WALL-CUSTOM (nth next-seg-real-idx *segment-list*)))) (setq next-vals (parse-h-spec next-spec)))
             (setq h-next (nth 0 next-vals) b-next (nth 1 next-vals))
             (if (or (> h-next h) (and (= h-next h) (> b-next b))) (setq h-end h-next b-end b-next tf-end (nth 3 next-vals)))
          )
        )
        (if prev-def
          (progn
            (setq start-is-corner T start-vertex (nth start-idx orig-vertices) start-prev (nth (if is-closed (if (= start-idx 0) (- n-verts 1) (- start-idx 1)) (- start-idx 1)) orig-vertices) start-next (nth (if is-closed (if (= start-idx (- n-verts 1)) 0 (+ start-idx 1)) (+ start-idx 1)) orig-vertices))
            (setq start-hpile-info (calculate-corner-params start-vertex start-prev start-next h-start b-start timber-offset boundary-orient))
            (setq start-limit (get-hpile-limit-offset (car start-hpile-info) h-start b-start tf-start (cadr start-hpile-info) pt1 seg-angle T (nth 2 start-hpile-info)))
          )
          (progn
            (setq start-pile-pt (polar pt1 seg-angle (/ b 2.0)))
            (entmake (list '(0 . "INSERT") (cons 2 hpile-block) '(8 . "_측면말뚝") (cons 10 start-pile-pt) '(41 . 1.0) '(42 . 1.0) '(43 . 1.0) (cons 50 hpile-rotation)))
            (setq *tsp-hpile-points* (append *tsp-hpile-points* (list start-pile-pt)))
            (setq start-limit (+ (/ b 2.0) 25.0) start-pile-placed T start-is-corner nil)
          )
        )
        (if next-def
          (progn
            (setq end-is-corner T end-vertex (nth end-idx orig-vertices) end-prev (nth (if is-closed (if (= end-idx 0) (- n-verts 1) (- end-idx 1)) (- end-idx 1)) orig-vertices) end-next (nth (if is-closed (if (= end-idx (- n-verts 1)) 0 (+ end-idx 1)) (+ end-idx 1)) orig-vertices))
            (setq end-hpile-info (calculate-corner-params end-vertex end-prev end-next h-end b-end timber-offset boundary-orient))
            (setq end-limit (get-hpile-limit-offset (car end-hpile-info) h-end b-end tf-end (cadr end-hpile-info) pt1 seg-angle nil (nth 2 end-hpile-info)))
          )
          (progn
            (setq end-pile-pt (polar pt2 (+ seg-angle pi) (/ b 2.0)))
            (entmake (list '(0 . "INSERT") (cons 2 hpile-block) '(8 . "_측면말뚝") (cons 10 end-pile-pt) '(41 . 1.0) '(42 . 1.0) '(43 . 1.0) (cons 50 hpile-rotation)))
            (setq *tsp-hpile-points* (append *tsp-hpile-points* (list end-pile-pt)))
            (setq end-limit (- seg-length (+ (/ b 2.0) 25.0)) end-pile-placed T end-is-corner nil)
          )
        )

        (if (<= start-limit end-limit)
          (progn
            (setq final-piles '())
            (setq final-timbers '())
            
            ;; [독립 벽체 모드] 기존 방식대로 중앙(Mid-pt) 기준 양쪽 대칭 배열
            (setq piles-A '() count-A 0 theory-count-A 0 i 0) (while (<= (* (+ i 0.5) ctc-mm) (/ seg-length 2.0)) (foreach dir '(1.0 -1.0) (setq theory-count-A (1+ theory-count-A) temp-dist (* (+ i 0.5) ctc-mm dir) center (+ (/ seg-length 2.0) temp-dist)) (if (and (> center (+ start-limit (/ b 2.0))) (< center (- end-limit (/ b 2.0)))) (progn (setq piles-A (append piles-A (list (polar mid-pt seg-angle temp-dist))) count-A (1+ count-A))))) (setq i (1+ i)))
            (setq piles-B '() count-B 0 theory-count-B 1 center (/ seg-length 2.0)) (if (and (> center (+ start-limit (/ b 2.0))) (< center (- end-limit (/ b 2.0)))) (progn (setq piles-B (list mid-pt) count-B 1))) (setq i 1) (while (<= (* i ctc-mm) (/ seg-length 2.0)) (foreach dir '(1.0 -1.0) (setq theory-count-B (1+ theory-count-B) temp-dist (* i ctc-mm dir) center (+ (/ seg-length 2.0) temp-dist)) (if (and (> center (+ start-limit (/ b 2.0))) (< center (- end-limit (/ b 2.0)))) (progn (setq piles-B (append piles-B (list (polar mid-pt seg-angle temp-dist))) count-B (1+ count-B))))) (setq i (1+ i)))
            (cond ((< theory-count-B theory-count-A) (setq use-method-B T)) ((> theory-count-B theory-count-A) (setq use-method-B nil)) (t (if (>= count-B count-A) (setq use-method-B T) (setq use-method-B nil))))
            (if use-method-B (setq final-piles piles-B) (setq final-piles piles-A))
            (if use-method-B (progn (setq i 0) (while (<= (* (+ i 0.5) ctc-mm) (+ (/ seg-length 2.0) ctc-mm)) (foreach dir '(1.0 -1.0) (setq temp-dist (* (+ i 0.5) ctc-mm dir) center (+ (/ seg-length 2.0) temp-dist) final-timbers (append final-timbers (list (cons (- center (/ timber-width 2.0)) (+ center (/ timber-width 2.0))))))) (setq i (1+ i)))) (progn (setq center (/ seg-length 2.0) final-timbers (list (cons (- center (/ timber-width 2.0)) (+ center (/ timber-width 2.0)))) i 1) (while (<= (* i ctc-mm) (+ (/ seg-length 2.0) ctc-mm)) (foreach dir '(1.0 -1.0) (setq temp-dist (* i ctc-mm dir) center (+ (/ seg-length 2.0) temp-dist) final-timbers (append final-timbers (list (cons (- center (/ timber-width 2.0)) (+ center (/ timber-width 2.0))))))) (setq i (1+ i)))))
            
            (setq mid-pile-count (length final-piles))
            (setq final-timbers (vl-sort final-timbers (function (lambda (a b) (< (car a) (car b))))))
            (setq valid-timbers '()) (foreach range final-timbers (setq potential-start (max (car range) start-limit) potential-end (min (cdr range) end-limit)) (if (> (- potential-end potential-start) 100.0) (setq valid-timbers (append valid-timbers (list (cons potential-start potential-end)))))) (setq final-timbers valid-timbers)
            (setq timber-idx 0 total-timbers (length final-timbers))
            (foreach range final-timbers
              (setq safe-start (car range) safe-end (cdr range) final-width (- safe-end safe-start) final-center-dist (/ (+ safe-start safe-end) 2.0))
              (setq timber-pt (polar pt1 seg-angle final-center-dist) timber-pt-offset (polar timber-pt outward-normal (- timber-offset)))
              (setq timber-result (create-timber-panel-object timber-pt-offset final-width current-thick seg-angle) top-left (nth 1 timber-result) top-right (nth 2 timber-result))
              ;; [간섭 배제]
              (setq cur-brace (cdr (assoc 'CORNER-BRACE seg-data)))
              (setq next-brace nil)
              (if (and next-seg-real-idx (< next-seg-real-idx (length *segment-list*)))
                (setq next-brace (cdr (assoc 'CORNER-BRACE (nth next-seg-real-idx *segment-list*))))
              )
              (setq dist-to-start final-center-dist dist-to-end (- seg-length final-center-dist) brace-blocked nil)
              ;; 상향 띠장(Upgraded Wale) 구역을 포함한 사보강재/앵커 간섭 정밀 체크
              (setq c-upg-s (cdr (assoc 'UPGRADE-WALE (nth start-idx *segment-list*))))
              (setq has-upg-s (and c-upg-s (= (car c-upg-s) "Y")))
              (setq c-upg-e (cdr (assoc 'UPGRADE-WALE (nth next-seg-real-idx *segment-list*))))
              (setq has-upg-e (and c-upg-e (= (car c-upg-e) "Y")))
              (setq exact-L-start 0.0 exact-L-end 0.0)
              
              (setq min-limit-s 0.0 min-limit-e 0.0)
              (setq upg-center-s 0.0 upg-center-e 0.0)
              (setq exact-L-start 0.0 exact-L-end 0.0)
              
              ;; 1. 시작점(pt1) 사보강재 물리적 간섭 및 상향 띠장 기준점 계산
              (if (and cur-brace (= (car cur-brace) "Y") (cadr cur-brace))
                (progn
                  (setq chk-last-b-row (last (cadr cur-brace)))
                  (setq chk-b-h (nth 0 (cadr chk-last-b-row)))
                  (setq chk-edge (if (wcmatch (strcase (nth 0 chk-last-b-row)) "2H*") (* chk-b-h 1.5) (/ chk-b-h 2.0)))
                  (setq min-limit-s (+ (* (nth 2 chk-last-b-row) 1000.0) chk-edge 150.0))
                  (setq exact-L-start min-limit-s)
                )
              )
              (if has-upg-s
                (progn
                  (setq best-d 1e99)
                  (if final-piles
                    (foreach p final-piles
                      (setq d-dist (distance pt1 p))
                      (if (> (+ d-dist 150.0) min-limit-s)
                        (if (< d-dist best-d) (setq best-d d-dist))
                      )
                    )
                  )
                  (if (< best-d 1e90)
                    (progn
                      (setq upg-center-s best-d)
                      (setq exact-L-start (+ best-d 150.0))
                    )
                  )
                )
              )

              ;; 2. 끝점(pt2) 사보강재 물리적 간섭 및 상향 띠장 기준점 계산 (2H 규격 반영)
              (if (and next-brace (= (car next-brace) "Y") (cadr next-brace))
                (progn
                  (setq chk-last-b-row (last (cadr next-brace)))
                  (setq chk-b-h (nth 0 (cadr chk-last-b-row)))
                  (setq chk-edge (if (wcmatch (strcase (nth 0 chk-last-b-row)) "2H*") (* chk-b-h 1.5) (/ chk-b-h 2.0)))
                  (setq min-limit-e (+ (* (nth 2 chk-last-b-row) 1000.0) chk-edge 150.0))
                  (setq exact-L-end min-limit-e)
                )
              )
              (if has-upg-e
                (progn
                  (setq best-d 1e99)
                  (if final-piles
                    (foreach p final-piles
                      (setq d-dist (distance pt2 p))
                      (if (> (+ d-dist 150.0) min-limit-e)
                        (if (< d-dist best-d) (setq best-d d-dist))
                      )
                    )
                  )
                  (if (< best-d 1e90)
                    (progn
                      (setq upg-center-e best-d)
                      (setq exact-L-end (+ best-d 150.0))
                    )
                  )
                )
              )
              
              ;; 3. CTC 기준 전체 상향(Full Upgrade) 검사 - 띠장 로직과 완벽 동기화 (중심점 기준)
              (setq check-L-s (if has-upg-s upg-center-s 0.0))
              (setq check-L-e (if has-upg-e upg-center-e 0.0))
              
              (if (and (or (> check-L-s 0.0) (> check-L-e 0.0))
                       (< (- seg-length (+ check-L-s check-L-e)) (* ctc-mm 1.5)))
                (setq exact-L-start seg-length exact-L-end seg-length)
              )
              
              ;; 4. 최종 간섭 판별 (상향 띠장 구간 내에는 앵커 배치 불가)
              (if (or (<= dist-to-start exact-L-start) (<= dist-to-end exact-L-end))
                (setq brace-blocked T)
              )
              (if (and has-anchor (not brace-blocked))
                (progn
                  (create-layer-if-not-exists "_앵커(Anchor)" "6")
                  (setq cos-val (cos (* max-anchor-ang (/ pi 180.0))))
                  (setq proj-free (* max-anchor-free 1000.0 cos-val) proj-bond (* max-anchor-bond 1000.0 cos-val) proj-prot (* 150.0 cos-val))
                  (setq pt-base (polar timber-pt outward-normal wale-h))
                  (setq pt-free-end (polar pt-base (+ outward-normal pi) proj-free) pt-bond-end (polar pt-free-end (+ outward-normal pi) proj-bond))
                  (setq pt-h1 (polar pt-base (+ outward-normal (/ pi 2.0)) 100.0) pt-h2 (polar pt-base (- outward-normal (/ pi 2.0)) 100.0))
                  (setq pt-h3 (polar pt-h2 outward-normal 60.0) pt-h4 (polar pt-h1 outward-normal 60.0))
                  (entmake (list '(0 . "LWPOLYLINE") '(100 . "AcDbEntity") '(100 . "AcDbPolyline") (cons 8 "_앵커(Anchor)") (cons 62 6) '(90 . 4) '(70 . 1) (list 10 (car pt-h1) (cadr pt-h1)) (list 10 (car pt-h2) (cadr pt-h2)) (list 10 (car pt-h3) (cadr pt-h3)) (list 10 (car pt-h4) (cadr pt-h4))))
                  (setq pt-anchor-start (polar pt-base outward-normal (+ 60.0 proj-prot)))
                  (make-lw-line pt-anchor-start pt-base "_앵커(Anchor)" 6)
                  (make-lw-line pt-base pt-free-end "_앵커(Anchor)" 6)
                  (entmake (list '(0 . "LWPOLYLINE") '(100 . "AcDbEntity") '(100 . "AcDbPolyline") (cons 8 "_앵커(Anchor)") (cons 62 6) '(90 . 2) '(70 . 0) '(43 . 400.0) (list 10 (car pt-free-end) (cadr pt-free-end)) (list 10 (car pt-bond-end) (cadr pt-bond-end))))
                )
              )
              (if (and (= timber-idx 0) (not start-is-corner) (not start-pile-placed)) (progn (setq left-offset-pt (polar top-left (+ seg-angle pi) edge-gap) left-hpile-pt (list (car left-offset-pt) (cadr timber-pt) 0.0)) (entmake (list '(0 . "INSERT") (cons 2 hpile-block) '(8 . "_측면말뚝") (cons 10 left-hpile-pt) '(41 . 1.0) '(42 . 1.0) '(43 . 1.0) (cons 50 hpile-rotation))) (setq *tsp-hpile-points* (append *tsp-hpile-points* (list left-hpile-pt)))))
              (if (and (= timber-idx (- total-timbers 1)) (not end-is-corner) (not end-pile-placed)) (progn (setq right-offset-pt (polar top-right seg-angle edge-gap) right-hpile-pt (list (car right-offset-pt) (cadr timber-pt) 0.0)) (entmake (list '(0 . "INSERT") (cons 2 hpile-block) '(8 . "_측면말뚝") (cons 10 right-hpile-pt) '(41 . 1.0) '(42 . 1.0) '(43 . 1.0) (cons 50 hpile-rotation))) (setq *tsp-hpile-points* (append *tsp-hpile-points* (list right-hpile-pt)))))
              (setq timber-idx (1+ timber-idx))
            )
            (foreach pt final-piles 
              (entmake (list '(0 . "INSERT") (cons 2 hpile-block) '(8 . "_측면말뚝") (cons 10 pt) '(41 . 1.0) '(42 . 1.0) '(43 . 1.0) (cons 50 hpile-rotation)))
              (setq *tsp-hpile-points* (append *tsp-hpile-points* (list pt)))
            )
          )
        )
      )
    )
    (setq *tsp-segment-pile-counts* (update-list-item *tsp-segment-pile-counts* seg-idx mid-pile-count))
    (setq seg-idx (1+ seg-idx))
  )
  ;; [코너 파일 작도]
      (setq idx 0)
      (while (< idx num-vertices)
        (setq prev-seg-idx (if (= idx 0) (if is-closed (1- num-vertices) -1) (1- idx)))
        (setq next-seg-idx (if (>= idx max-segments) -1 idx))
        (setq prev-def (if (>= prev-seg-idx 0) (cdr (assoc 'IS-DEFINED (nth prev-seg-idx *segment-list*))) nil))
        (setq next-def (if (>= next-seg-idx 0) (cdr (assoc 'IS-DEFINED (nth next-seg-idx *segment-list*))) nil))


        ;; 혼합 프로젝트에서 CIP와 CIP가 만나는 모서리에 불필요한 H-Pile 코너말뚝이 생성되는 것을 원천 차단
        (setq prev-type (if prev-def (cdr (assoc 'WALL-TYPE (nth prev-seg-idx *segment-list*))) "NONE"))
        (setq next-type (if next-def (cdr (assoc 'WALL-TYPE (nth next-seg-idx *segment-list*))) "NONE"))
        
        (if (and prev-def next-def)
          (progn
            (setq prev-vertex (nth prev-seg-idx orig-vertices) curr-vertex (nth idx orig-vertices) next-vertex (nth (if is-closed (if (= idx (1- num-vertices)) 0 (1+ idx)) (1+ idx)) orig-vertices))
            ;; [분기 1] 코너 말뚝 작도 (양쪽 세그먼트 중 하나라도 H-Pile일 때만 실행)
            (if (or (= prev-type "HPILE") (= next-type "HPILE"))
              (progn
                ;; prev-vertex, curr-vertex, next-vertex는 위 판별부에서 이미 설정됨
                (setq seg-data (nth prev-seg-idx *segment-list*))
                (setq prev-spec (cdr (assoc 'WALL-SPEC seg-data))) (if (= prev-spec "User-defined") (setq prev-vals (cdr (assoc 'WALL-CUSTOM seg-data))) (setq prev-vals (parse-h-spec prev-spec))) (setq h-prev (nth 0 prev-vals) b-prev (nth 1 prev-vals))
                (setq target-seg-data (nth next-seg-idx *segment-list*))
                (setq next-spec (cdr (assoc 'WALL-SPEC target-seg-data))) (if (= next-spec "User-defined") (setq next-vals (cdr (assoc 'WALL-CUSTOM target-seg-data))) (setq next-vals (parse-h-spec next-spec))) (setq h-next (nth 0 next-vals) b-next (nth 1 next-vals))
                (if (or (> h-next h-prev) (and (= h-next h-prev) (> b-next b-prev)))
                  (setq h h-next b b-next tw (nth 2 next-vals) tf (nth 3 next-vals) target-seg-data (nth next-seg-idx *segment-list*))
                  (setq h h-prev b b-prev tw (nth 2 prev-vals) tf (nth 3 prev-vals) target-seg-data (nth prev-seg-idx *segment-list*))
                )
                (setq current-thick (cdr (assoc 'TIMBER-THICKNESS target-seg-data))) (if (null current-thick) (setq current-thick 60)) (setq hpile-block (create-hpile-section-block h b tw tf)) (setq timber-offset (+ tf (/ current-thick 2.0)))
                (place-hpile-at-corner-simple curr-vertex (angle prev-vertex curr-vertex) (angle curr-vertex next-vertex) h b tw tf hpile-block timber-offset boundary-orient prev-vertex next-vertex)
              )
            )
          )
        )
        (setq idx (1+ idx))
      )
      (princ "\nH-Pile 및 토류판 작도 완료!")
    )


;;;;==========================================================================
;;;; defun tsp-draw-closed-poly : 폴리라인 작도 범용 유틸리티 (모듈화 분리)
;;;;==========================================================================
(defun tsp-draw-closed-poly (pts layer color / lst p)
  (setq lst (list '(0 . "LWPOLYLINE") '(100 . "AcDbEntity") '(100 . "AcDbPolyline") (cons 8 layer) (cons 62 color) (cons 90 (length pts)) '(70 . 1)))
  (foreach p pts (setq lst (append lst (list (list 10 (car p) (cadr p))))))
  (entmake lst)
)

;;;;==========================================================================
;;;; defun tsp-draw-wedge-connection : 화타쐐기 작도 및 가림 판정용 다각형 외곽선 반환
;;;;==========================================================================
(defun tsp-draw-wedge-connection (pt_inner p1_flange p2_flange strut_dir wale_dir wale_norm conn_type / 
                                  p1_wall p2_wall vW dot pExt_wall pOth_wall isExt2 
                                  p1 p2 p3 fill_1 fill_2 dist_f1 dist_f2 half_bp
                                  wp_1 wp_2 wp_3 wp_4 ep_b1 ep_b2 ep_t1 ep_t2
                                  p1_foot_temp p1_temp l2_p2_temp p2_temp p2_foot_temp
                                  dir_to_p2 dir_to_p1 p2_foot p1_foot
                                  p1_14 p2_14 p1_64 p2_64 p_cut p2_end p3_end br_p1 br_p2 wedge_segs get-poly-segs)

  ;; 다각형 정점들로부터 닫힌 선분 리스트를 추출하는 내부 함수
  (defun get-poly-segs (pts / segs i)
    (setq segs '() i 0)
    (while (< i (length pts))
      (setq segs (append segs (list (list (nth i pts) (nth (if (= i (1- (length pts))) 0 (1+ i)) pts)))))
      (setq i (1+ i))
    )
    segs
  )

  (setq wedge_segs '())
  ;; 1. 사보강재 진행 방향(isExt2) 판별 로직
  (setq p1_wall (inters p1_flange (polar p1_flange strut_dir 100.0) pt_inner (polar pt_inner wale_dir 100.0) nil))
  (setq p2_wall (inters p2_flange (polar p2_flange strut_dir 100.0) pt_inner (polar pt_inner wale_dir 100.0) nil))
  (setq vW (list (- (car p2_wall) (car p1_wall)) (- (cadr p2_wall) (cadr p1_wall))))
  (setq dot (+ (* (car vW) (cos strut_dir)) (* (cadr vW) (sin strut_dir))))
  (if (> dot 0)
    (setq isExt2 T pExt_wall p2_wall pOth_wall p1_wall)
    (setq isExt2 nil pExt_wall p1_wall pOth_wall p2_wall)
  )

  ;; 3. 연결 방식(conn_type)에 따른 작도 및 다각형 추출 분기
  (if (= conn_type "화타쐐기 없음")
    (progn
      (setq p1 pt_inner)
      (setq p2 (polar p1 wale_norm 14.0))

      (setq fill_1 (inters p1_flange (polar p1_flange strut_dir 100.0) p2 (polar p2 wale_dir 100.0) nil))
      (setq fill_2 (inters p2_flange (polar p2_flange strut_dir 100.0) p2 (polar p2 wale_dir 100.0) nil))

      (setq dist_f1 (distance p2 fill_1))
      (setq dist_f2 (distance p2 fill_2))
      (setq half_bp (max 250.0 (+ (max dist_f1 dist_f2) 50.0)))

      (setq wp_3 (polar p2 (+ wale_dir pi) half_bp))
      (setq wp_4 (polar p2 wale_dir half_bp))
      (setq wp_1 (polar wp_4 (+ wale_norm pi) 14.0))
      (setq wp_2 (polar wp_3 (+ wale_norm pi) 14.0))
      (tsp-draw-closed-poly (list wp_1 wp_2 wp_3 wp_4) "_화타쐐기(Wedge)" 2)
      (setq wedge_segs (append wedge_segs (get-poly-segs (list wp_1 wp_2 wp_3 wp_4))))

      (setq p3 (polar p2 strut_dir 220.0))
      (setq ep_b1 (inters p3 (polar p3 (+ strut_dir (/ pi 2.0)) 100.0) p1_flange (polar p1_flange strut_dir 100.0) nil))
      (setq ep_b2 (inters p3 (polar p3 (+ strut_dir (/ pi 2.0)) 100.0) p2_flange (polar p2_flange strut_dir 100.0) nil))

      (tsp-draw-closed-poly (list ep_b1 ep_b2 fill_2 fill_1) "_화타쐐기(Wedge)" 2)
      (setq wedge_segs (append wedge_segs (get-poly-segs (list ep_b1 ep_b2 fill_2 fill_1))))

      (setq ep_t1 (polar ep_b1 strut_dir 14.0))
      (setq ep_t2 (polar ep_b2 strut_dir 14.0))
      (tsp-draw-closed-poly (list ep_b1 ep_b2 ep_t2 ep_t1) "_화타쐐기(Wedge)" 2)
      (setq wedge_segs (append wedge_segs (get-poly-segs (list ep_b1 ep_b2 ep_t2 ep_t1))))

      (if isExt2
        (setq br_p1 ep_t2 br_p2 ep_t1)
        (setq br_p1 ep_t1 br_p2 ep_t2)
      )
    )
    (progn
      (setq p1_foot_temp pOth_wall)
      (setq p1_temp (polar p1_foot_temp wale_norm 64.0))
      (setq l2_p2_temp (polar p1_temp (angle pOth_wall pExt_wall) 100.0))
      (setq p2_temp (inters p1_temp l2_p2_temp pExt_wall (polar pExt_wall strut_dir 100.0) nil))
      (setq p2_foot_temp (polar p2_temp (+ wale_norm pi) 64.0))

      (setq dir_to_p2 (angle pt_inner p2_foot_temp))
      (setq dir_to_p1 (+ dir_to_p2 pi))
      (setq p2_foot (polar pt_inner dir_to_p2 (distance pt_inner p2_foot_temp)))
      (setq p1_foot (polar pt_inner dir_to_p1 (distance pt_inner p2_foot_temp)))

      (setq p1_14 (polar p1_foot wale_norm 14.0))
      (setq p1_64 (polar p1_foot wale_norm 64.0))
      (setq p2_14 (polar p2_foot wale_norm 14.0))
      (setq p2_64 p2_temp)

      (setq p_cut (inters p2_64 (polar p2_64 (+ strut_dir (/ pi 2.0)) 100.0) pOth_wall (polar pOth_wall strut_dir 100.0) nil))
      (setq p2_end (polar p2_64 strut_dir 14.0))
      (setq p3_end (polar p_cut strut_dir 14.0))

      (tsp-draw-closed-poly (list p1_foot p2_foot p2_14 p1_14) "_화타쐐기(Wedge)" 2)
      (setq wedge_segs (append wedge_segs (get-poly-segs (list p1_foot p2_foot p2_14 p1_14))))
      
      (tsp-draw-closed-poly (list p1_14 p1_64 p_cut p2_64 p2_14) "_화타쐐기(Wedge)" 2)
      (setq wedge_segs (append wedge_segs (get-poly-segs (list p1_14 p1_64 p_cut p2_64 p2_14))))
      
      (tsp-draw-closed-poly (list p2_64 p_cut p3_end p2_end) "_화타쐐기(Wedge)" 2)
      (setq wedge_segs (append wedge_segs (get-poly-segs (list p2_64 p_cut p3_end p2_end))))

      (if isExt2
        (setq br_p1 p3_end br_p2 p2_end)
        (setq br_p1 p2_end br_p2 p3_end)
      )
    )
  )

  ;; 잭 삽입점 및 가림 판정용 다각형 선분 동시 반환
  (list br_p1 br_p2 wedge_segs)
)


;;;;==========================================================================
;;;; defun tsp-draw-all-corner-braces : 사보강재(Corner Strut) 및 다중 대칭 보강재(Brace Array) 작도 통합 모듈
;;;;==========================================================================
(defun tsp-draw-all-corner-braces (boundary-ent boundary-orient / boundary-handle is-closed orig-vertices num-vertices max-segments idx prev-seg-idx next-seg-idx prev-def next-def prev-vertex curr-vertex next-vertex p-brace c-upg upg-vals prev-wale-spec prev-wale-vals w-h-prev next-wale-spec next-wale-vals w-h-next dir-A dir-B norm-A norm-B brace-b-rows b-row-idx b-spec b-custom b-dist-m b-jack b-conn b-dist b-h half-w pt-A-base pt-B-base pt-A-inner pt-B-inner brace-dir L1-A L1-B L2-A L2-B pA1 pA2 pB1 pB2 conn_pts_A conn_pts_B brace_A1 brace_A2 brace_B1 brace_B2 jack-side jack-len pt-jack-ins jack-rot brace_A1_in brace_A2_in brace_B1_in brace_B2_in b-tw half-tw mid_A_in mid_B_in web1_A web1_B web2_A web2_B max_brace_len brace_boundaries stiff-h stiff-tw pt_A_face_p1 pt_B_face_p1 pt-inner-corner vec_A vec_B vec_sum stiff-dir half-ang brace_len slender-limit is-manual manual-interval stiff-enable stiff-margin L-max total-L num-div interval cur-off offsets off axis-p1 axis-p2 p_out_L_line p_out_R_line pA_inf1 pA_inf2 pB_inf1 pB_inf2 hit-L_A hit-L_B hit-R_A hit-R_B hit-L hit-R proj-L proj-R max-proj hit-C_A hit-C_B hit-C p_flat_center p_flat_L p_flat_R p_stiff_base_center p_stiff_base_L p_stiff_base_R p_start_center p_out_L p_out_R p_in_L p_in_R max_dist_overall p_x1 p_x2 d1 d2 current_d merged_intervals sorted last_m pt_from pt_to p_end_L p_end_R valid-hit intervals cur_int hit-A hit-B hit-Wale wall-norm wl_dir ang_diff flat-half-w p_w1 p_w2 p_f1 p_f2 p_fL p_fR d_foot p_foot_A p_foot_B p_flat_A p_flat_B p_stiff_base_A p_stiff_base_B)

  (defun valid-hit (hit p-cor dir)
    (if hit (if (> (tsp-project-dist p-cor dir hit) -1e-3) hit nil) nil)
  )

  ;; 객체의 고유 핸들을 추출하여 변수에 저장
  (setq boundary-handle (tsp-get-entity-handle boundary-ent))
  
  (setq is-closed (is-closed-polyline boundary-ent))
  (setq orig-vertices (mapcar '(lambda (item) (cdr (assoc 'V-START item))) *segment-list*))
  (if (not is-closed) (setq orig-vertices (append orig-vertices (list (cdr (assoc 'V-END (last *segment-list*)))))))
  (setq num-vertices (length orig-vertices))
  (setq max-segments (if is-closed num-vertices (1- num-vertices)))

  (setq idx 0)
  (while (< idx num-vertices)
    (setq prev-seg-idx (if (= idx 0) (if is-closed (1- num-vertices) -1) (1- idx)))
    (setq next-seg-idx (if (>= idx max-segments) -1 idx))
    (setq prev-def (if (>= prev-seg-idx 0) (cdr (assoc 'IS-DEFINED (nth prev-seg-idx *segment-list*))) nil))
    (setq next-def (if (>= next-seg-idx 0) (cdr (assoc 'IS-DEFINED (nth next-seg-idx *segment-list*))) nil))
    
    (if (and prev-def next-def)
      (progn
        (setq prev-vertex (nth prev-seg-idx orig-vertices) curr-vertex (nth idx orig-vertices) next-vertex (nth (if is-closed (if (= idx (1- num-vertices)) 0 (1+ idx)) (1+ idx)) orig-vertices))
        (setq p-brace nil)
        (if (and (>= idx 0) (< idx (length *segment-list*))) (setq p-brace (cdr (assoc 'CORNER-BRACE (nth idx *segment-list*)))))
        
        (if (and p-brace (= (car p-brace) "Y"))
          (progn
            (setq brace-b-rows (cadr p-brace))
            (setq slender-limit (if (> (length p-brace) 2) (nth 2 p-brace) "1"))
            (setq is-manual (if (> (length p-brace) 3) (nth 3 p-brace) "0"))
            (setq manual-interval (if (> (length p-brace) 4) (nth 4 p-brace) "0.0"))
            (setq stiff-enable (if (> (length p-brace) 5) (nth 5 p-brace) "1"))
            (setq stiff-margin (if (> (length p-brace) 6) (atof (nth 6 p-brace)) 50.0))

            (setq c-upg (cdr (assoc 'UPGRADE-WALE (nth idx *segment-list*))))
            (setq upg-vals (if (and c-upg (= (car c-upg) "Y")) (parse-h-spec (cadr c-upg)) nil))
            
            ;; 띠장(Wale) 오프셋 작도 로직과 완벽히 동기화되도록 '기본 띠장'과 '상향 띠장' 중 최대값(max)을 적용
            (setq prev-wale-spec (cdr (assoc 'WALE-SPEC (nth prev-seg-idx *segment-list*))))
            (setq prev-wale-vals (if (= prev-wale-spec "User-defined") (cdr (assoc 'WALE-CUSTOM (nth prev-seg-idx *segment-list*))) (parse-h-spec prev-wale-spec)))
            (setq base-h-prev (if prev-wale-vals (nth 0 prev-wale-vals) 300))
            (setq w-h-prev (if upg-vals (max (nth 0 upg-vals) base-h-prev) base-h-prev))
            
            (setq next-wale-spec (cdr (assoc 'WALE-SPEC (nth next-seg-idx *segment-list*))))
            (setq next-wale-vals (if (= next-wale-spec "User-defined") (cdr (assoc 'WALE-CUSTOM (nth next-seg-idx *segment-list*))) (parse-h-spec next-wale-spec)))
            (setq base-h-next (if next-wale-vals (nth 0 next-wale-vals) 300))
            (setq w-h-next (if upg-vals (max (nth 0 upg-vals) base-h-next) base-h-next))
            
            (setq dir-A (angle curr-vertex prev-vertex) dir-B (angle curr-vertex next-vertex))
            (setq norm-A (+ (angle prev-vertex curr-vertex) (* boundary-orient (/ pi 2.0))))
            (setq norm-B (+ (angle curr-vertex next-vertex) (* boundary-orient (/ pi 2.0))))
            
            (setq b-row-idx 0 max_brace_len 0.0 brace_boundaries '() stiff-h 300.0 stiff-tw 10.0 brace-row-data-list '())
            
            (setq pt_A_face_p1 (polar curr-vertex norm-A w-h-prev))
            (setq pt_B_face_p1 (polar curr-vertex norm-B w-h-next))
            (setq pt-inner-corner (inters pt_A_face_p1 (polar pt_A_face_p1 dir-A 100.0) pt_B_face_p1 (polar pt_B_face_p1 dir-B 100.0) nil))
            (if (null pt-inner-corner) (setq pt-inner-corner curr-vertex))
            
            ;; 굴착면 안쪽을 향하도록 법선(norm) 벡터를 합산
            (setq vec_nA (list (cos norm-A) (sin norm-A)))
            (setq vec_nB (list (cos norm-B) (sin norm-B)))
            (setq vec_n_sum (list (+ (car vec_nA) (car vec_nB)) (+ (cadr vec_nA) (cadr vec_nB))))
            (setq stiff-dir (angle '(0 0 0) vec_n_sum))
            
            ;; 모서리 내각(delta)의 절반을 삼각함수로 안전하게 산출
            (setq delta (abs (- dir-A dir-B)))
            (if (> delta pi) (setq delta (- (* 2.0 pi) delta)))
            (setq half-ang (/ delta 2.0))
            
            (create-strut-jack-block) (create-strut-screw-jack-block)
            (if (not (tblsearch "APPID" "TSP_STRUT_SPEC")) (regapp "TSP_STRUT_SPEC"))
            
              ;;;; 사보강재 단일/맞버팀대(Double Strut) 작도 로직
              (foreach b-row brace-b-rows
                (setq b-spec (nth 0 b-row) b-custom (nth 1 b-row) b-dist-m (nth 2 b-row) b-jack (nth 3 b-row) b-conn (nth 4 b-row))
                (if (null b-jack) (setq b-jack "스크류잭"))
                (if (null b-conn) (setq b-conn (if (= b-row-idx 0) "화타쐐기 없음" "화타쐐기 TYPE-G1")))
                
                (setq b-dist (* b-dist-m 1000.0) b-h (nth 0 b-custom) b-width (nth 1 b-custom) half-w (/ b-width 2.0) stiff-h b-h stiff-tw (nth 2 b-custom))
                
                (setq pt-A-base (polar curr-vertex dir-A b-dist) pt-B-base (polar curr-vertex dir-B b-dist))
                (setq pt-A-inner (list (car (polar pt-A-base norm-A w-h-prev)) (cadr (polar pt-A-base norm-A w-h-prev)) 0.0))
                (setq pt-B-inner (list (car (polar pt-B-base norm-B w-h-next)) (cadr (polar pt-B-base norm-B w-h-next)) 0.0))
                
                (create-layer-if-not-exists "_mpoint" "2")
                (entmake (list '(0 . "POINT") '(100 . "AcDbEntity") '(100 . "AcDbPoint") (cons 8 "_mpoint") (cons 62 2) (list 10 (car pt-A-inner) (cadr pt-A-inner) 0.0)))
                (entmake (list '(0 . "POINT") '(100 . "AcDbEntity") '(100 . "AcDbPoint") (cons 8 "_mpoint") (cons 62 2) (list 10 (car pt-B-inner) (cadr pt-B-inner) 0.0)))

                (setq brace-dir (angle pt-A-inner pt-B-inner))
                (setq is-double (wcmatch b-spec "2H *"))
                (setq strut-offsets (if is-double (list b-width (- b-width)) (list 0.0)))
                
                (setq sub-idx 0)
                (foreach s-off strut-offsets
                  (setq off-dir (+ brace-dir (/ pi 2.0)))
                  (setq p-off-A (polar pt-A-inner off-dir s-off))
                  (setq p-off-B (polar pt-B-inner off-dir s-off))
                  
                  (setq sub-pt-A-inner (inters pt-A-inner (polar pt-A-inner dir-A 100.0) p-off-A p-off-B nil))
                  (setq sub-pt-B-inner (inters pt-B-inner (polar pt-B-inner dir-B 100.0) p-off-A p-off-B nil))
                  
                  (if (and sub-pt-A-inner sub-pt-B-inner)
                    (progn
                      (setq sub-brace_len (distance sub-pt-A-inner sub-pt-B-inner))
                      (if (> sub-brace_len max_brace_len) (setq max_brace_len sub-brace_len))
                      
                      (setq sub-brace-dir (angle sub-pt-A-inner sub-pt-B-inner))
                      (setq L1-A (polar sub-pt-A-inner (+ sub-brace-dir (/ pi 2.0)) half-w) L1-B (polar sub-pt-B-inner (+ sub-brace-dir (/ pi 2.0)) half-w))
                      (setq L2-A (polar sub-pt-A-inner (- sub-brace-dir (/ pi 2.0)) half-w) L2-B (polar sub-pt-B-inner (- sub-brace-dir (/ pi 2.0)) half-w))
                      
                      (setq pA1 (inters sub-pt-A-inner (polar sub-pt-A-inner dir-A 100.0) L1-A L1-B nil))
                      (setq pA2 (inters sub-pt-A-inner (polar sub-pt-A-inner dir-A 100.0) L2-A L2-B nil))
                      (setq pB1 (inters sub-pt-B-inner (polar sub-pt-B-inner dir-B 100.0) L1-A L1-B nil))
                      (setq pB2 (inters sub-pt-B-inner (polar sub-pt-B-inner dir-B 100.0) L2-A L2-B nil))
                      
                      (create-layer-if-not-exists "_사보강재(Corner_Strut)" "3") (create-layer-if-not-exists "_화타쐐기(Wedge)" "2")
                      
                      (if (and pA1 pB1 pA2 pB2)
                        (progn
                          (setq conn_pts_A (tsp-draw-wedge-connection sub-pt-A-inner pA1 pA2 sub-brace-dir dir-A norm-A b-conn))
                          (setq brace_A1 (car conn_pts_A) brace_A2 (cadr conn_pts_A) wedge_segs_A (caddr conn_pts_A))
                          
                          (setq conn_pts_B (tsp-draw-wedge-connection sub-pt-B-inner pB1 pB2 (+ sub-brace-dir pi) dir-B norm-B b-conn))
                          (setq brace_B1 (car conn_pts_B) brace_B2 (cadr conn_pts_B) wedge_segs_B (caddr conn_pts_B))
                          
                          ;; 맞버팀대(2H) 교차 배치 로직 적용
                          (if is-double
                            (setq jack-side (if (= sub-idx 0) "A" "B"))
                            (progn
                              (setq jack-side nil) 
                              (if (> b-row-idx 0) (if (= (rem b-row-idx 2) 1) (setq jack-side "A") (setq jack-side "B")))
                            )
                          )
                          
                          (setq jack-len 583.0)
                          (if (= jack-side "A")
                            (progn
                              (setq pt-jack-ins (list (/ (+ (car brace_A1) (car brace_A2)) 2.0) (/ (+ (cadr brace_A1) (cadr brace_A2)) 2.0) 0.0) jack-rot sub-brace-dir)
                              (entmake (list '(0 . "INSERT") (cons 2 b-jack) (cons 8 (if (= b-jack "스크류잭") "_스크류잭" "_유압잭")) (cons 62 2) (cons 10 pt-jack-ins) '(41 . 1.0) '(42 . 1.0) '(43 . 1.0) (cons 50 jack-rot)))
                              (setq brace_A1 (polar brace_A1 sub-brace-dir jack-len) brace_A2 (polar brace_A2 sub-brace-dir jack-len))
                            )
                          )
                          (if (= jack-side "B")
                            (progn
                              (setq pt-jack-ins (list (/ (+ (car brace_B1) (car brace_B2)) 2.0) (/ (+ (cadr brace_B1) (cadr brace_B2)) 2.0) 0.0) jack-rot (+ sub-brace-dir pi))
                              (entmake (list '(0 . "INSERT") (cons 2 b-jack) (cons 8 (if (= b-jack "스크류잭") "_스크류잭" "_유압잭")) (cons 62 2) (cons 10 pt-jack-ins) '(41 . 1.0) '(42 . 1.0) '(43 . 1.0) (cons 50 jack-rot)))
                              (setq brace_B1 (polar brace_B1 (+ sub-brace-dir pi) jack-len) brace_B2 (polar brace_B2 (+ sub-brace-dir pi) jack-len))
                            )
                          )
                          (tsp-draw-closed-poly (list brace_A1 brace_A2 brace_B2 brace_B1) "_사보강재(Corner_Strut)" 3)
                          
                          (setq cur-seg-id (cdr (assoc 'ID (nth idx *segment-list*))))
                          (setq outer-margin (* 2.0 (+ (if is-double b-width 0.0) half-w 100.0)))
                          (setq pA_bound (polar pt-A-inner dir-A outer-margin))
                          (setq pB_bound (polar pt-B-inner dir-B outer-margin))
                          
                          (setq strut-xdata 
                            (list -3 
                              (list "TSP_STRUT_SPEC" 
                                (cons 1070 cur-seg-id) 
                                (cons 1040 (float b-h)) 
                                (cons 1040 (float b-width)) 
                                (cons 1040 (float (nth 2 b-custom))) 
                                (cons 1040 (float (nth 3 b-custom)))
                                (cons 1010 pt-inner-corner)
                                (cons 1010 pA_bound)
                                (cons 1010 pB_bound)
                                (cons 1000 boundary-handle)
                              )
                            )
                          )
                          
                          (entmod (append (entget (entlast)) (list strut-xdata)))
                          
                          (setq brace_A1_in (polar brace_A1 sub-brace-dir 14.0) brace_A2_in (polar brace_A2 sub-brace-dir 14.0))
(setq brace_B1_in (polar brace_B1 (+ sub-brace-dir pi) 14.0) brace_B2_in (polar brace_B2 (+ sub-brace-dir pi) 14.0))

(setq half-tw (/ (nth 2 b-custom) 2.0))
(setq mid_A_in (list (/ (+ (car brace_A1_in) (car brace_A2_in)) 2.0) (/ (+ (cadr brace_A1_in) (cadr brace_A2_in)) 2.0) 0.0))
(setq mid_B_in (list (/ (+ (car brace_B1_in) (car brace_B2_in)) 2.0) (/ (+ (cadr brace_B1_in) (cadr brace_B2_in)) 2.0) 0.0))
(setq web1_A (polar mid_A_in (+ sub-brace-dir (/ pi 2.0)) half-tw) web1_B (polar mid_B_in (+ sub-brace-dir (/ pi 2.0)) half-tw))
(setq web2_A (polar mid_A_in (- sub-brace-dir (/ pi 2.0)) half-tw) web2_B (polar mid_B_in (- sub-brace-dir (/ pi 2.0)) half-tw))
(if (not (tblsearch "LTYPE" "DASHED")) (vl-catch-all-apply 'vla-load (list (vla-get-linetypes (vla-get-activedocument (vlax-get-acad-object))) "DASHED" "acad.lin")))
(entmake 
  (append 
    (list 
      '(0 . "LWPOLYLINE") 
      '(100 . "AcDbEntity") 
      '(100 . "AcDbPolyline") 
      (cons 8 "_사보강재(Corner_Strut)") 
      (cons 62 1) 
      (cons 6 "DASHED") 
      (cons 48 (* (if (and (boundp '*tsp-scale-plan*) *tsp-scale-plan*) *tsp-scale-plan* 600.0) (/ 500.0 600.0) (if (= (getvar "MEASUREMENT") 1) (/ 1.0 25.0) 1.0)))
      '(90 . 2) 
      '(70 . 0) 
      (list 10 (car web1_A) (cadr web1_A)) 
      (list 10 (car web1_B) (cadr web1_B))
    ) 
    (list strut-xdata)
  )
)
(entmake 
  (append 
    (list 
      '(0 . "LWPOLYLINE") 
      '(100 . "AcDbEntity") 
      '(100 . "AcDbPolyline") 
      (cons 8 "_사보강재(Corner_Strut)") 
      (cons 62 1) 
      (cons 6 "DASHED") 
      (cons 48 (* (if (and (boundp '*tsp-scale-plan*) *tsp-scale-plan*) *tsp-scale-plan* 600.0) (/ 500.0 600.0) (if (= (getvar "MEASUREMENT") 1) (/ 1.0 25.0) 1.0)))
      '(90 . 2) 
      '(70 . 0) 
      (list 10 (car web2_A) (cadr web2_A)) 
      (list 10 (car web2_B) (cadr web2_B))
    ) 
    (list strut-xdata)
  )
)
                          
                          (setq brace_boundaries (append brace_boundaries 
                            (list 
                              (cons "WEDGE" (list (list brace_A1 brace_B1) (list brace_B1 brace_B2) (list brace_B2 brace_A2) (list brace_A2 brace_A1)))
                              (cons "WEDGE" wedge_segs_A)
                              (cons "WEDGE" wedge_segs_B)
                                )))
                        )
                      )
                    )
                  )
                  (setq sub-idx (1+ sub-idx))
                )
                
                ;; 현재 사보강재 열의 핵심 데이터(중심선, 방향, 맞버팀대 여부, 폭, 규격)를 리스트에 보존
                (setq brace-row-data-list (append brace-row-data-list (list (list pt-A-inner pt-B-inner brace-dir is-double b-width half-w b-custom))))
                
                (setq b-row-idx (1+ b-row-idx))
              )


            ;; [3] 다중 대칭 보강재(Brace Array) 작도 및 동적 간섭/절단 엔진 (옵션에 따라 통제됨)
            (if (and (> (length brace-b-rows) 0) (= stiff-enable "1"))
              (progn
                (setq L-max (tsp-calc-unsupported-length (nth 1 (last brace-b-rows)) (if (= slender-limit "0") 100.0 120.0)))
                (setq total-L (/ max_brace_len 1000.0))
                
                (setq offsets '())
                (if (> total-L L-max)
                  (progn
                    (create-layer-if-not-exists "_보강재(Brace)" "7")
                   (if (= is-manual "1")
                      (progn
                        (setq interval (* (atof manual-interval) 1000.0))
                        (if (<= interval 0.01)
                          (setq offsets (list 0.0))
                          (progn
                            (setq cur-off interval offsets (list 0.0))
                            (while (<= cur-off (/ max_brace_len 2.0))
                              (setq offsets (append offsets (list cur-off (- cur-off))) cur-off (+ cur-off interval))
                            )
                          )
                        )
                      )
                      (progn
                        (setq num-div (fix (+ (/ total-L L-max) 0.9999)) interval (/ max_brace_len num-div) i 1)
                        (while (< i num-div)
                          (setq off (- (* i interval) (/ max_brace_len 2.0)) offsets (append offsets (list off)) i (1+ i))
                        )
                      )
                    )
                  )
                )

                (setq pA_inf1 pt-inner-corner pA_inf2 (polar pt-inner-corner dir-A 100.0))
                (setq pB_inf1 pt-inner-corner pB_inf2 (polar pt-inner-corner dir-B 100.0))
                (setq stiff-half-w (/ stiff-h 2.0))

               ;; 중간말뚝 옵션 읽기 및 좌/우 설정 초기화
                (setq post-enable (if (> (length p-brace) 7) (nth 7 p-brace) "1"))
                (setq post-side (if (> (length p-brace) 8) (nth 8 p-brace) "L"))
                ;; 9번째 인덱스의 배치 모드 (0=전체, 1=교차)
                (setq post-layout (if (> (length p-brace) 9) (nth 9 p-brace) "1"))
                ;; 10번째 인덱스의 교차 반전 모드 (0=기본, 1=반전)
                (setq post-invert (if (> (length p-brace) 10) (nth 10 p-brace) "0"))

                (setq stiff-idx 0) ;; 보강재(가로축) 인덱스 초기화
                (foreach off offsets
                  (setq draw-this-brace nil)
                  (setq hit-Wale nil)
                  
                  (if (equal off 0.0 1e-4)
                    (progn
                      (setq d_foot (/ stiff-half-w (sin half-ang)))
                      (setq p_start_center (polar pt-inner-corner stiff-dir (+ (* d_foot (cos half-ang)) 28.0)))
                      (setq draw-this-brace T)
                    )
                    (progn
                      (setq axis-p1 (polar pt-inner-corner brace-dir off) axis-p2 (polar axis-p1 stiff-dir 100.0))
                      (setq hit-A (inters axis-p1 axis-p2 pA_inf1 pA_inf2 nil))
                      (setq hit-B (inters axis-p1 axis-p2 pB_inf1 pB_inf2 nil))
                      
                      (setq hit-Wale nil wall-norm nil wl_dir nil)
                      (if (valid-hit hit-A pt-inner-corner dir-A) (setq hit-Wale hit-A wall-norm norm-A wl_dir dir-A)
                        (if (valid-hit hit-B pt-inner-corner dir-B) (setq hit-Wale hit-B wall-norm norm-B wl_dir dir-B))
                      )
                      
                      (if hit-Wale
                        (progn
                          (setq p_bp_center hit-Wale)
                          (setq p_ep_center (polar p_bp_center stiff-dir 220.0))
                          (setq p_start_center (polar p_ep_center stiff-dir 14.0))
                          (setq draw-this-brace T)
                        )
                      )
                    )
                  )
                  
                 (if draw-this-brace
                    (progn
                      (if (= post-enable "1")
                        (progn
                          (create-layer-if-not-exists "_중간말뚝(Post pile)" "3")
                          
                          (setq row-idx 0) ;; 사보강재 열(세로축) 인덱스 초기화
                          (foreach br-data brace-row-data-list
                            (setq cur-pt-A-inner (list (car (nth 0 br-data)) (cadr (nth 0 br-data)) 0.0)
                                  cur-pt-B-inner (list (car (nth 1 br-data)) (cadr (nth 1 br-data)) 0.0)
                                  cur-brace-dir  (nth 2 br-data)
                                  cur-is-double  (nth 3 br-data)
                                  cur-b-width    (nth 4 br-data)
                                  cur-half-w     (nth 5 br-data)
                                  cur-b-custom   (nth 6 br-data)
                                  cur-h          (nth 0 cur-b-custom)
                                  cur-b          (nth 1 cur-b-custom)
                                  cur-tw         (nth 2 cur-b-custom)
                                  cur-tf         (nth 3 cur-b-custom))
                            
                            ;; 동적 말뚝 블록 생성
                            (setq post-block (create-post-pile-block cur-h cur-b cur-tw cur-tf))
                            
                            (setq p_stiff_2d (list (car p_start_center) (cadr p_start_center) 0.0))
                            (setq p_stiff_end (polar p_stiff_2d stiff-dir 1000.0))
                            
                            (setq cross-pt (inters cur-pt-A-inner cur-pt-B-inner p_stiff_2d p_stiff_end nil))
                            
                           (if cross-pt
                              (progn
                                ;; 현재 사보강재 열의 길이 및 유효성 플래그 초기화
                                (setq cur-brace-len (distance cur-pt-A-inner cur-pt-B-inner))
                                (setq is-valid-post T)
                                
                                ;; 1. 세장비 초과 검사 (최대거리를 초과하는 경우에만 생성)
                                (if (<= cur-brace-len (* L-max 1000.0))
                                  (progn
                                    (setq is-valid-post nil)
                                  )
                                )
                                
                                ;; 2. 띠장 간섭 및 최소 이격거리 확보 (+ 300.0 cur-h 연동)
                                (if (and is-valid-post (<= (tsp-project-dist p_start_center stiff-dir cross-pt) (+ 300.0 cur-h)))
                                  (progn
                                    (setq is-valid-post nil)
                                  )
                                )

                                ;; 3. 교차(지그재그) 배치 검사 및 반전(Invert) 적용
                                (if (and is-valid-post (= post-layout "1"))
                                  (progn
                                    (setq spatial-idx 0)
                                    (if (> interval 0.01)
                                      (setq spatial-idx (fix (if (> off 0) (+ (/ off interval) 0.5) (- (/ off interval) 0.5))))
                                    )
                                    (setq invert-val (if (= post-invert "1") 1 0))
                                    ;; 공간 인덱스, 사보강재 열 인덱스, 반전값을 합산하여 홀/짝 판별
                                    (if (/= (rem (+ spatial-idx row-idx invert-val) 2) 0)
                                      (setq is-valid-post nil)
                                    )
                                  )
                                )
                                
                                ;; 조건 만족 시에만 중간말뚝 작도
                                (if is-valid-post
                                  (progn
                                    ;; [1단계] 기본 형태인 '왼쪽(L)' 기준으로 1H/2H 고유 좌표 및 회전각 산출
                                    (if cur-is-double
                                      (progn
                                        ;; 2H: 왼쪽 측면 밀착
                                        (setq pt-post-ins (polar cross-pt (- stiff-dir (/ pi 2.0)) stiff-half-w))
                                        (setq post-rot (+ stiff-dir pi))
                                      )
                                      (progn
                                        ;; 1H: 왼쪽 보강재 외곽선과 사보강재 내측면의 교차점을 통한 역산
                                        (setq stiff-left-p1 (polar p_stiff_2d (- stiff-dir (/ pi 2.0)) stiff-half-w))
                                        (setq stiff-left-p2 (polar p_stiff_end (- stiff-dir (/ pi 2.0)) stiff-half-w))
                                        (setq cs-norm1 (+ cur-brace-dir (/ pi 2.0)))
                                        (setq cs-norm2 (- cur-brace-dir (/ pi 2.0)))
                                        (setq cp1 (polar cross-pt cs-norm1 cur-half-w))
                                        (setq cp2 (polar cross-pt cs-norm2 cur-half-w))
                                        (setq cs-inner-pt (if (< (distance cp1 p_stiff_2d) (distance cp2 p_stiff_2d)) cp1 cp2))
                                        (setq cs-inner-p2 (polar cs-inner-pt cur-brace-dir 100.0))
                                        (setq pt-target (inters stiff-left-p1 stiff-left-p2 cs-inner-pt cs-inner-p2 nil))
                                        (setq post-rot (+ cur-brace-dir (/ pi 2.0)))
                                        (if pt-target
                                          (setq pt-post-ins (polar pt-target post-rot (/ cur-h 2.0)))
                                          (setq pt-post-ins cross-pt) ; 보험용
                                        )
                                      )
                                    )

                                    ;; [2단계]
                                    (setq y_scale 1.0)

                                    ;; [3단계] 사용자 옵션 '오른쪽(R)' 선택 시에만 기하학적 대칭적용
                                    (if (= post-side "R")
                                      (progn
                                        (setq post-rot (- (* 2.0 stiff-dir) post-rot))
                                        (setq dist-to-ins (distance cross-pt pt-post-ins))
                                        (setq ang-to-ins (angle cross-pt pt-post-ins))
                                        (setq mirror-ang (- (* 2.0 stiff-dir) ang-to-ins))
                                        (setq pt-post-ins (polar cross-pt mirror-ang dist-to-ins))
                                        (setq y_scale -1.0)
                                      )
                                    )
                                    (entmake (list '(0 . "INSERT") (cons 2 post-block) (cons 8 "_중간말뚝(Post pile)") (cons 62 256) (cons 10 pt-post-ins) '(41 . 1.0) (cons 42 y_scale) '(43 . 1.0) (cons 50 post-rot)))
                                  )
                                )
                              )
                            )
                            (setq row-idx (1+ row-idx)) 
                          )
                        )
                      )
                      (setq max_dist_overall 0.0)
                      (foreach b_bounds brace_boundaries
                        (if (= (car b_bounds) "WEDGE")
                          (foreach seg (cdr b_bounds)
                            (setq p_x1 (inters p_start_center (polar p_start_center stiff-dir 1e6) (car seg) (cadr seg) T))
                            (if p_x1
                              (progn
                                (setq d1 (tsp-project-dist p_start_center stiff-dir p_x1))
                                (if (> d1 max_dist_overall) (setq max_dist_overall d1))
                              )
                            )
                          )
                        )
                      )
                      (setq total_L (+ max_dist_overall stiff-margin)) ;; 돌출 길이에 사용자 지정 여유장 변수 할당

                      (if (> total_L 1000.0)
                        (progn
                          (setq p_out_L (polar p_start_center (+ stiff-dir (/ pi 2.0)) stiff-half-w))
                          (setq p_out_R (polar p_start_center (- stiff-dir (/ pi 2.0)) stiff-half-w))
                          (setq p_in_L (polar p_start_center (+ stiff-dir (/ pi 2.0)) (/ stiff-tw 2.0)))
                          (setq p_in_R (polar p_start_center (- stiff-dir (/ pi 2.0)) (/ stiff-tw 2.0)))
                          
                          (if (equal off 0.0 1e-4)
                            (progn
                              (setq p_foot_A (polar pt-inner-corner dir-A d_foot))
                              (setq p_foot_B (polar pt-inner-corner dir-B d_foot))
                              (setq p_flat_A (polar p_foot_A stiff-dir 14.0))
                              (setq p_flat_B (polar p_foot_B stiff-dir 14.0))
                              
                              (entmake (list '(0 . "LWPOLYLINE") '(100 . "AcDbEntity") '(100 . "AcDbPolyline") (cons 8 "_화타쐐기(Wedge)") (cons 62 2) '(90 . 3) '(70 . 0) (list 10 (car p_foot_A) (cadr p_foot_A)) (list 10 (car pt-inner-corner) (cadr pt-inner-corner)) (list 10 (car p_foot_B) (cadr p_foot_B))))
                              (tsp-draw-closed-poly (list p_foot_A p_foot_B p_flat_B p_flat_A) "_화타쐐기(Wedge)" 2)
                              
                              (setq p_stiff_base_A (polar p_flat_A stiff-dir 14.0))
                              (setq p_stiff_base_B (polar p_flat_B stiff-dir 14.0))
                              (tsp-draw-closed-poly (list p_flat_A p_flat_B p_stiff_base_B p_stiff_base_A) "_보강재(Brace)" 256)
                            )
                            (progn
                             (defun draw-trimmed-line (p-s p-e l-name l-color / dist-total pt-dir intervals b-bounds px px1 px2 d1 d2 hits sorted merged cur-d pt-from pt-to last_m seg p-ray-start p-ray-end dx dy perp-dist)
                                (setq dist-total (distance p-s p-e))
                                (if (> dist-total 0.001)
                                  (progn
                                    (setq pt-dir (angle p-s p-e))
                                    (setq intervals '())
                                    (foreach b_bounds brace_boundaries
                                      (setq hits '())
                                      (if (= (car b_bounds) "WEDGE")
                                        (progn
                                          (setq p-ray-start (polar p-s pt-dir -1e6))
                                          (setq p-ray-end (polar p-s pt-dir 1e6))
                                          (foreach seg (cdr b_bounds)
                                            (setq px (inters p-ray-start p-ray-end (car seg) (cadr seg) T))
                                            (if px 
                                              (setq hits (append hits (list (tsp-project-dist p-s pt-dir px))))
                                              (progn
                                                (setq dx (- (car (car seg)) (car p-s)))
                                                (setq dy (- (cadr (car seg)) (cadr p-s)))
                                                (setq perp-dist (abs (- (* dx (sin pt-dir)) (* dy (cos pt-dir)))))
                                                (if (< perp-dist 0.1)
                                                  (setq hits (append hits (list (tsp-project-dist p-s pt-dir (car seg)) 
                                                                                (tsp-project-dist p-s pt-dir (cadr seg)))))
                                                )
                                              )
                                            )
                                          )
                                        )
                                      )
                                      (if (>= (length hits) 1)
                                        (progn
                                          (setq hits (vl-sort hits '<))
                                          (setq d1 (max 0.0 (min dist-total (car hits))))
                                          (setq d2 (max 0.0 (min dist-total (last hits))))
                                          (if (not (equal d1 d2 0.01))
                                            (setq intervals (append intervals (list (cons d1 d2))))
                                          )
                                        )
                                      )
                                    )
                                    (setq merged '())
                                    (if intervals
                                      (progn
                                        (setq sorted (vl-sort intervals (function (lambda (a b) (< (car a) (car b))))))
                                        (setq merged (list (car sorted)))
                                        (foreach cur (cdr sorted)
                                          (setq last_m (last merged))
                                          (if (<= (car cur) (cdr last_m))
                                            (setq merged (subst (cons (car last_m) (max (cdr last_m) (cdr cur))) last_m merged))
                                            (setq merged (append merged (list cur)))
                                          )
                                        )
                                      )
                                    )
                                    (setq cur-d 0.0)
                                    (foreach cur-int merged
                                      (if (> (car cur-int) (+ cur-d 0.01))
                                        (progn
                                          (setq pt-from (polar p-s pt-dir cur-d))
                                          (setq pt-to (polar p-s pt-dir (car cur-int)))
                                          (entmake (list '(0 . "LWPOLYLINE") '(100 . "AcDbEntity") '(100 . "AcDbPolyline")
                                                         (cons 8 l-name) (cons 62 l-color) '(90 . 2) '(70 . 0)
                                                         (list 10 (car pt-from) (cadr pt-from)) (list 10 (car pt-to) (cadr pt-to))))
                                        )
                                      )
                                      (setq cur-d (max cur-d (cdr cur-int)))
                                    )
                                    (if (< cur-d (- dist-total 0.01))
                                      (progn
                                        (setq pt-from (polar p-s pt-dir cur-d))
                                        (setq pt-to (polar p-s pt-dir dist-total))
                                        (entmake (list '(0 . "LWPOLYLINE") '(100 . "AcDbEntity") '(100 . "AcDbPolyline")
                                                       (cons 8 l-name) (cons 62 l-color) '(90 . 2) '(70 . 0)
                                                       (list 10 (car pt-from) (cadr pt-from)) (list 10 (car pt-to) (cadr pt-to))))
                                      )
                                    )
                                  )
                                )
                              )

                              (setq p_fill_L (inters p_out_L (polar p_out_L stiff-dir 100.0) p_bp_center (polar p_bp_center wl_dir 100.0) nil))
                              (setq p_fill_R (inters p_out_R (polar p_out_R stiff-dir 100.0) p_bp_center (polar p_bp_center wl_dir 100.0) nil))
                              (if (null p_fill_L) (setq p_fill_L p_bp_center))
                              (if (null p_fill_R) (setq p_fill_R p_bp_center))
                              
                              (setq half_bp (max 250.0 (+ (max (distance p_bp_center p_fill_L) (distance p_bp_center p_fill_R)) 50.0)))
                              
                              (setq p_bp_top_L (polar p_bp_center wl_dir half_bp))
                              (setq p_bp_top_R (polar p_bp_center (+ wl_dir pi) half_bp))
                              
                              (setq p_ep_bot_L (polar p_ep_center (+ stiff-dir (/ pi 2.0)) stiff-half-w))
                              (setq p_ep_bot_R (polar p_ep_center (- stiff-dir (/ pi 2.0)) stiff-half-w))
                              (setq p_ep_top_L p_out_L)
                              (setq p_ep_top_R p_out_R)
                              
                              (setq wedge-layer "_화타쐐기(Wedge)")
                              (setq wedge-color 2)
                              
                              (draw-trimmed-line p_bp_top_L p_bp_top_R wedge-layer wedge-color)
                              (draw-trimmed-line p_fill_L p_ep_bot_L wedge-layer wedge-color)
                              (draw-trimmed-line p_fill_R p_ep_bot_R wedge-layer wedge-color)
                              (draw-trimmed-line p_ep_bot_L p_ep_bot_R wedge-layer wedge-color)
                              (draw-trimmed-line p_ep_bot_L p_ep_top_L wedge-layer wedge-color)
                              (draw-trimmed-line p_ep_bot_R p_ep_top_R wedge-layer wedge-color)
                              (draw-trimmed-line p_ep_top_L p_ep_top_R wedge-layer wedge-color)
                            )
                          )

                          (foreach line_def (list (list p_out_L 256 "BYLAYER") (list p_out_R 256 "BYLAYER") (list p_in_L 1 "DASHED") (list p_in_R 1 "DASHED"))
                            (setq p_start (car line_def) col (cadr line_def) ltype (caddr line_def) intervals '())
                            
                            (setq adj_total_L (- total_L (tsp-project-dist p_start_center stiff-dir p_start)))
                            
                            (foreach b_bounds brace_boundaries
                              (setq hits '())
                              (if (= (car b_bounds) "WEDGE")
                                (progn
                                  (setq ray_start (polar p_start stiff-dir -1e6))
                                  (setq ray_end (polar p_start stiff-dir 1e6))
                                  (foreach seg (cdr b_bounds)
                                    (setq p_x1 (inters ray_start ray_end (car seg) (cadr seg) T))
                                    (if p_x1 
                                      (setq hits (append hits (list (tsp-project-dist p_start stiff-dir p_x1))))
                                      (progn
                                        (setq dx_col (- (car (car seg)) (car p_start)))
                                        (setq dy_col (- (cadr (car seg)) (cadr p_start)))
                                        (setq p_dist_col (abs (- (* dx_col (sin stiff-dir)) (* dy_col (cos stiff-dir)))))
                                        (if (< p_dist_col 0.1)
                                          (setq hits (append hits (list (tsp-project-dist p_start stiff-dir (car seg)) 
                                                                        (tsp-project-dist p_start stiff-dir (cadr seg)))))
                                        )
                                      )
                                    )
                                  )
                                )
                              )
                              (if (>= (length hits) 1)
                                (progn
                                  (setq hits (vl-sort hits '<))
                                  (setq d1 (max 0.0 (car hits)))
                                  (setq d2 (max 0.0 (last hits)))
                                  (if (not (equal d1 d2 0.01))
                                    (setq intervals (append intervals (list (cons d1 d2))))
                                  )
                                )
                              )
                            )
                            (setq merged_intervals '())
                            (if intervals
                              (progn
                                (setq sorted (vl-sort intervals (function (lambda (a b) (< (car a) (car b))))))
                                (setq merged_intervals (list (car sorted)))
                                (foreach cur (cdr sorted)
                                  (setq last_m (last merged_intervals))
                                  (if (<= (car cur) (cdr last_m))
                                    (setq merged_intervals (subst (cons (car last_m) (max (cdr last_m) (cdr cur))) last_m merged_intervals))
                                    (setq merged_intervals (append merged_intervals (list cur)))
                                  )
                                )
                              )
                            )
                            (setq current_d 0.0)
                            (foreach cur_int merged_intervals
                              (if (> (car cur_int) current_d)
                                (progn
                                  (setq pt_from (polar p_start stiff-dir current_d) pt_to (polar p_start stiff-dir (car cur_int)))
                                  (entmake (list '(0 . "LWPOLYLINE") '(100 . "AcDbEntity") '(100 . "AcDbPolyline") (cons 8 "_보강재(Brace)") (cons 62 col) (if (= ltype "DASHED") (cons 6 "DASHED") '(6 . "BYLAYER")) (if (= ltype "DASHED") (cons 48 (* (if (and (boundp '*tsp-scale-plan*) *tsp-scale-plan*) *tsp-scale-plan* 600.0) (/ 500.0 600.0) (if (= (getvar "MEASUREMENT") 1) (/ 1.0 25.0) 1.0))) '(48 . 1.0)) '(90 . 2) '(70 . 0) (list 10 (car pt_from) (cadr pt_from)) (list 10 (car pt_to) (cadr pt_to))))
                                )
                              )
                              (setq current_d (cdr cur_int))
                            )
                            (if (< current_d adj_total_L)
                              (progn
                                (setq pt_from (polar p_start stiff-dir current_d) pt_to (polar p_start stiff-dir adj_total_L))
                                (entmake (list '(0 . "LWPOLYLINE") '(100 . "AcDbEntity") '(100 . "AcDbPolyline") (cons 8 "_보강재(Brace)") (cons 62 col) (if (= ltype "DASHED") (cons 6 "DASHED") '(6 . "BYLAYER")) (if (= ltype "DASHED") (cons 48 (* (if (and (boundp '*tsp-scale-plan*) *tsp-scale-plan*) *tsp-scale-plan* 600.0) (/ 500.0 600.0) (if (= (getvar "MEASUREMENT") 1) (/ 1.0 25.0) 1.0))) '(48 . 1.0)) '(90 . 2) '(70 . 0) (list 10 (car pt_from) (cadr pt_from)) (list 10 (car pt_to) (cadr pt_to))))
                              )
                            )
                          )
                          
                          (setq p_end_center (polar p_start_center stiff-dir total_L))
                          (setq p_end_L (polar p_end_center (+ stiff-dir (/ pi 2.0)) stiff-half-w))
                          (setq p_end_R (polar p_end_center (- stiff-dir (/ pi 2.0)) stiff-half-w))
                          (entmake (list '(0 . "LWPOLYLINE") '(100 . "AcDbEntity") '(100 . "AcDbPolyline") (cons 8 "_보강재(Brace)") (cons 62 256) '(90 . 2) '(70 . 0) (list 10 (car p_end_L) (cadr p_end_L)) (list 10 (car p_end_R) (cadr p_end_R))))
                        )
                      )
                    )
                  )
                  (setq stiff-idx (1+ stiff-idx))
                )
              )
            )
          )
        )
      )
    )
    (setq idx (1+ idx))
  )
  (princ)
)


;;;;==========================================================================
;;;; defun create-hpile-set-on-boundary : 평면도 생성 (H-Pile / C.I.P 분기 처리 적용)
;;;;==========================================================================
(defun create-hpile-set-on-boundary (boundary-ent boundary-orient / last-ent vertices
                                      seg-data seg-wall-type has-cip has-hpile i
                                      vla-bnd total-len s-item s-manual-pts s-sec-str s-jack-type
                                      remapped-pts p d new-pt s-pt1 s-pt2 draw-result)

  ;; 1. 기존 그룹 정리 (번호표 포함 모든 객체 삭제)
  (tsp-clear-drawing-group boundary-ent)
  ;; 2. 마지막 엔티티 추적 시작 (가장 완벽한 위치)
  (setq last-ent (entlast))

  ;; 모든 세그먼트의 말뚝 개수를 누적할 전역 리스트를 0으로 사전 초기화
  (setq *tsp-segment-pile-counts* '())
  (setq i 0)
  (while (< i (length *segment-list*))
    (setq *tsp-segment-pile-counts* (cons 0 *tsp-segment-pile-counts*))
    (setq i (1+ i))
  )
  (setq *tsp-segment-pile-counts* (reverse *tsp-segment-pile-counts*))

  ;; 데이터 캐싱을 위한 H-Pile 좌표 리스트 초기화
  (setq *tsp-hpile-points* '())

  ;; 3. 안전망(vl-catch-all-apply) 구축: 내부 로직에서 에러가 발생해도 튕기지 않도록 보호
  (setq draw-result 
    (vl-catch-all-apply
      '(lambda ()
         ;; 4-1. 세그먼트에 CIP / HPILE 이 섞여있는지 파악
         (setq has-cip nil  has-hpile nil)
         (if *segment-list*
           (foreach seg-data *segment-list*
             (if (cdr (assoc 'IS-DEFINED seg-data))
               (progn
                 (setq seg-wall-type (cdr (assoc 'WALL-TYPE seg-data)))
                 (if (= seg-wall-type "CIP")
                   (setq has-cip T)
                   (setq has-hpile T)
                 )
               )
             )
           )
         )
         ;; 4-2. H-Pile+토류판 세그먼트 작도
         (if has-hpile
           (progn
             (princ "\n[작도] H-Pile 및 토류판 생성 중...")
             (place-hpile-timber-along-boundary boundary-ent boundary-orient)
           )
         )
         ;; 4-3. CIP 세그먼트 작도
         (if has-cip
           (progn
             (princ "\n[작도] C.I.P(현장타설말뚝) 배열 생성 중...")
             (tsp-draw-cip-plan-per-segment boundary-ent boundary-orient)
           )
         )
         ;; 4-4. 전역값 폴백 (안전장치)
         (if (and (not has-cip) (not has-hpile))
           (progn
             (if (= *tsp-wall-type* "CIP")
               (progn
                 (princ "\n[작도] C.I.P(현장타설말뚝) 배열 생성 중... (전역 폴백)")
                 (tsp-draw-cip-plan boundary-ent boundary-orient)
               )
               (progn
                 (princ "\n[작도] H-Pile 및 토류판 생성 중... (전역 폴백)")
                 (place-hpile-timber-along-boundary boundary-ent boundary-orient)
               )
             )
           )
         )

         ;; 5. 버팀보(Strut) 평면 재작도
         (if *segment-list*
           (progn
             (princ "\n[버팀보 재작도] 데이터 분석 및 작도 시작...")
             (setq vla-bnd (vlax-ename->vla-object boundary-ent))
             (setq total-len (vlax-curve-getdistatparam vla-bnd (vlax-curve-getendparam vla-bnd)))
             
             (setq poly-verts (mapcar '(lambda (x / v)
                                         (setq v (trans (cdr (assoc 'V-START x)) boundary-ent 0))
                                         (list (car v) (cadr v) 0.0)
                                       )
                                       *segment-list*))

             (foreach seg-data *segment-list*
               (foreach s-item (cdr (assoc 'SUPPORT-LIST seg-data))
                 (if (wcmatch (car s-item) "버팀보*")
                   (progn
                     (princ (strcat "\n[버팀보 확인] 이름: " (nth 1 s-item) " 데이터 로드 중..."))
                     (setq s-shape      (if (> (length s-item) 2) (nth 2 s-item) "H형강"))
                     (setq s-sec-str    (if (> (length s-item) 6) (nth 6 s-item) ""))
                     (setq s-jack-type  (if (> (length s-item) 7) (nth 7 s-item) ""))
                     (setq s-manual-pts (if (> (length s-item) 8) (nth 8 s-item) nil))

                     (if s-manual-pts
                       (princ (strcat "\n  -> 수집된 점 데이터 개수: " (itoa (length s-manual-pts))))
                       (princ "\n  -> 수집된 점 데이터가 없습니다 (nil).")
                     )

                     (if (and s-manual-pts (>= (length s-manual-pts) 1))
                       (progn
                         (setq remapped-pts '())
                         (foreach p s-manual-pts
                           (setq p-on-curve (vl-catch-all-apply 'vlax-curve-getClosestPointTo (list vla-bnd p)))
                           (if (not (vl-catch-all-error-p p-on-curve))
                             (setq d (vl-catch-all-apply 'vlax-curve-getdistatpoint (list vla-bnd p-on-curve)))
                             (setq d nil)
                           )
                           (if (or (vl-catch-all-error-p d) (null d)) (setq d 0.0))
                           (if (> d total-len) (setq d total-len))
                           (setq new-pt (vlax-curve-getpointatdist vla-bnd d))
                           (setq remapped-pts (cons new-pt remapped-pts))
                         )
                         (setq remapped-pts (reverse remapped-pts))
                         (princ (strcat "\n  -> 경계선 좌표 매핑 성공. 총 " (itoa (length remapped-pts)) "개의 기준점에서 레이저 투사 시작."))

                         (setq draw-count 0)
                         (foreach bp remapped-pts
                           (setq min-dist 1e99 seg-idx1 0 i 0 best-seg1 nil)
                           (foreach seg *segment-list*
                             (setq p1 (cdr (assoc 'V-START seg)))
                             (setq p2 (cdr (assoc 'V-END seg)))
                             (setq d (abs (- (+ (distance p1 bp) (distance bp p2)) (distance p1 p2))))
                             (if (< d min-dist)
                               (progn (setq min-dist d seg-idx1 i best-seg1 seg))
                             )
                             (setq i (1+ i))
                           )

                           (setq p-base-flat (list (car bp) (cadr bp) 0.0))
                           (setq p1 (trans (cdr (assoc 'V-START best-seg1)) boundary-ent 0))
                           (setq p2 (trans (cdr (assoc 'V-END best-seg1)) boundary-ent 0))
                           (setq p1 (list (car p1) (cadr p1) 0.0))
                           (setq p2 (list (car p2) (cadr p2) 0.0))

                           (setq tang-ang (angle p1 p2))
                           (setq norm-ang1 (+ tang-ang (/ pi 2.0)))
                           (setq norm-ang2 (- tang-ang (/ pi 2.0)))

                           (setq p-ray1 (polar p-base-flat norm-ang1 1e6))
                           (setq p-ray2 (polar p-base-flat norm-ang2 1e6))

                           (setq pts '() i 0)
                           (foreach seg *segment-list*
                             (setq sp1 (trans (cdr (assoc 'V-START seg)) boundary-ent 0))
                             (setq sp2 (trans (cdr (assoc 'V-END seg)) boundary-ent 0))
                             (setq sp1-flat (list (car sp1) (cadr sp1) 0.0))
                             (setq sp2-flat (list (car sp2) (cadr sp2) 0.0))

                             (setq int-pt1 (inters p-base-flat p-ray1 sp1-flat sp2-flat T))
                             (setq int-pt2 (inters p-base-flat p-ray2 sp1-flat sp2-flat T))

                             (if (and int-pt1 (> (distance p-base-flat int-pt1) 10.0))
                               (setq pts (cons (list int-pt1 i norm-ang1) pts))
                             )
                             (if (and int-pt2 (> (distance p-base-flat int-pt2) 10.0))
                               (setq pts (cons (list int-pt2 i norm-ang2) pts))
                             )
                             (setq i (1+ i))
                           )
                           (setq pts (reverse pts))

                           (setq valid-pts '())
                           (foreach pt-data pts
                             (setq int-pt (car pt-data))
                             (setq mid-pt (list (/ (+ (car p-base-flat) (car int-pt)) 2.0) (/ (+ (cadr p-base-flat) (cadr int-pt)) 2.0) 0.0))
                             (if (tsp-is-point-inside mid-pt poly-verts)
                               (setq valid-pts (cons pt-data valid-pts))
                             )
                           )
                           (setq valid-pts (reverse valid-pts))

                           (if valid-pts
                             (progn
                               (setq valid-pts (vl-sort valid-pts '(lambda (a b) (< (distance p-base-flat (car a)) (distance p-base-flat (car b))))))
                               (setq p-opp (car (car valid-pts)))
                               (setq seg-idx2 (cadr (car valid-pts)))
                               (setq norm-ang (caddr (car valid-pts)))

                               (setq offset1 (tsp-get-wale-offset (nth seg-idx1 *segment-list*)))
                               (setq offset2 (tsp-get-wale-offset (nth seg-idx2 *segment-list*)))

                               (if (> (distance bp p-opp) (+ offset1 offset2))
                                 (progn
                                   (setq pt1-draw (polar bp norm-ang offset1))
                                   (setq pt2-draw (polar p-opp (+ norm-ang pi) offset2))

                                   (if (wcmatch s-shape "H형강")
                                     (progn
                                       ;; 1. 개수를 파악하여 2H 맞버팀대 여부(is-double) 결정
                                       (setq s-count (if (> (length s-item) 4) (nth 4 s-item) 1))
                                       (setq is-double (if (>= s-count 2) T nil))
                                       ;; 2. 보강재 및 중간말뚝 옵션 추출
                                       (setq s-brace-opt (if (> (length s-item) 11) (nth 11 s-item) nil))
                                       ;; 3. 현재 작도 기준점이 속한 세그먼트의 고유 ID 추출
                                       (setq cur-seg-id (cdr (assoc 'ID best-seg1)))
                                       ;; _mpoint 레이어 POINT 객체 생성
                                       (create-layer-if-not-exists "_mpoint" "2")
                                       (entmake (list '(0 . "POINT") '(100 . "AcDbEntity") '(100 . "AcDbPoint") (cons 8 "_mpoint") (cons 62 2) (list 10 (car pt1-draw) (cadr pt1-draw) 0.0)))
                                       (entmake (list '(0 . "POINT") '(100 . "AcDbEntity") '(100 . "AcDbPoint") (cons 8 "_mpoint") (cons 62 2) (list 10 (car pt2-draw) (cadr pt2-draw) 0.0)))
                                       ;; 7개의 인수를 모두 전달하여 버팀보 및 부속물 통합 작도
                                       (tsp-draw-manual-strut pt1-draw pt2-draw s-sec-str s-jack-type is-double s-brace-opt cur-seg-id)
                                       (setq draw-count (1+ draw-count))
                                     )
                                   )
                                 )
                               )
                             )
                           )
                         ) ;; foreach bp end
                         (princ (strcat "\n  -> [최종 완료] 도면에 작도된 버팀보 묶음 개수: " (itoa draw-count)))
                       )
                     )
                   )
                 )
               )
             )
           )
         )

         ;; 6. 사보강재, 띠장, 번호표 통합 작도
         (princ "\n[작도] 사보강재(Corner Brace) 생성 중...")
         (tsp-draw-all-corner-braces boundary-ent boundary-orient)

         (princ "\n[작도] 띠장(Wale) 생성 중...")
         (create-wale-offsets boundary-ent boundary-orient)

         (if *segment-list*
           (progn
             (setq vertices (mapcar '(lambda (item) (cdr (assoc 'V-START item))) *segment-list*))
             (if (not (is-closed-polyline boundary-ent))
               (setq vertices (append vertices (list (cdr (assoc 'V-END (last *segment-list*))))))
             )
             (draw-segment-numbers boundary-ent boundary-orient vertices)
             (draw-corner-numbers boundary-ent boundary-orient vertices)
           )
         )
      ) ; lambda 종료
    ) ; catch-all-apply 종료
  ) ; setq 종료

;; =======================================================================
  ;; 7. [핵심] 무슨 일이 있어도 그룹화는 무조건 실행시켜 고아 객체 발생 차단
  ;; =======================================================================
  (tsp-group-last-entities last-ent boundary-ent)
  
  (if boundary-ent
    (vl-catch-all-apply
      '(lambda ( / v-bnd ms dict sort-ents arr)
         (setq v-bnd (vlax-ename->vla-object boundary-ent))
         (setq ms (vla-ObjectIdToObject (vla-get-Document v-bnd) (vla-get-OwnerId v-bnd)))
         (setq dict (vla-GetExtensionDictionary ms))
         (setq sort-ents (vl-catch-all-apply 'vla-GetObject (list dict "ACAD_SORTENTS")))
         (if (vl-catch-all-error-p sort-ents)
           (setq sort-ents (vla-AddObject dict "ACAD_SORTENTS" "AcDbSortentsTable"))
         )
         (setq arr (vlax-make-safearray vlax-vbobject '(0 . 0)))
         (vlax-safearray-put-element arr 0 v-bnd)
         (vla-MoveToTop sort-ents arr)
       )
    )
  )
  
  (vl-catch-all-apply 'vla-regen (list (vla-get-activedocument (vlax-get-acad-object)) 1))

  ;; 8. 내부에서 충돌(Crash)이 발생했다면, 커맨드창에 붉은 글로 에러 내용 보고
  (if (vl-catch-all-error-p draw-result)
    (princ (strcat "\n[에러 알림] 버팀보 작도 중 내부 충돌이 발생했습니다. (객체 추적은 정상 보존됨)\n상세 원인: " (vl-catch-all-error-message draw-result)))
    (princ "\n평면도 생성 및 갱신 완료.")
  )
)

;;;;==========================================================================
;;;; defun tsp-ceil :  숫자 올림 보조 함수 (LISP 기본 기능 보완)
;;;;==========================================================================
(defun tsp-ceil (val)
  (if (= (type val) 'INT)
    val
    (if (= val (float (fix val)))
      (fix val)
      (1+ (fix val))
    )
  )
)


;;;;==========================================================================
;;;; defun tsp-create-cip-guideline : 외측 방향을 고려한 D/2 오프셋 보조선 생성
;;;;==========================================================================
(defun tsp-create-cip-guideline (boundary-ent dia boundary-orient is-closed / vobj d start-pt p2 seg-angle out-norm target-pt off-obj off-ent closest-pt)
  (setq vobj (vlax-ename->vla-object boundary-ent))
  ;; dia가 문자열인지 숫자인지 판별하여 안전하게 처리 (에러 방지)
  (setq d (/ (if (= (type dia) 'STR) (atof dia) dia) 2.0))
  ;; H-Pile 로직에서 추출한 완벽한 외측 벡터 계산 (안팎 판별 오류 방지)
  (setq start-pt (vlax-curve-getStartPoint vobj))
  (setq p2 (vlax-curve-getPointAtParam vobj 1.0))
  (setq seg-angle (angle start-pt p2))
  (setq out-norm (+ seg-angle (* boundary-orient (/ pi 2.0))))
  ;; H-Pile과 완벽히 동일한 방식: 바깥쪽(흙 방향)을 향하도록 마이너스(-d) 적용
  (setq target-pt (polar start-pt out-norm (- d)))
  ;; 양수 거리로 오프셋 후, 수학적으로 계산된 target-pt와 일치하는지 교차 검증
  (setq off-obj (vl-catch-all-apply 'vla-offset (list vobj d)))
  (if (not (vl-catch-all-error-p off-obj))
    (progn
      (setq off-ent (vlax-vla-object->ename (vlax-safearray-get-element (vlax-variant-value off-obj) 0)))
      ;; 오프셋선 방향이 강제 반전되었을 때 시작점(off-start)이 달라지는 현상을 막기 위해,
      ;; target-pt와 가장 가까운 실제 폴리선 상의 점(closest-pt)을 도출하여 검증합니다.
      (setq closest-pt (vlax-curve-getClosestPointTo (vlax-ename->vla-object off-ent) target-pt))
      (if (> (distance (list (car target-pt) (cadr target-pt)) (list (car closest-pt) (cadr closest-pt))) 0.1)
        (progn
          (entdel off-ent)
          (setq off-obj (vl-catch-all-apply 'vla-offset (list vobj (- d))))
          (if (not (vl-catch-all-error-p off-obj))
            (setq off-ent (vlax-vla-object->ename (vlax-safearray-get-element (vlax-variant-value off-obj) 0)))
            (setq off-ent nil)
          )
        )
      )
      off-ent
    )
    nil
  )
)


;;;;==========================================================================
;;;; defun tsp-calc-cip-layout : 경계선(곡선)을 따라 C.I.P 중심점 배열 및 간격 계산
;;;;==========================================================================
(defun tsp-calc-cip-layout (curve-ent is-closed dia mode overlap / total-length target-pitch count actual-pitch i dist check-dist pt ang deriv centers next-dist)
  (setq total-length (vlax-curve-getdistatparam curve-ent (vlax-curve-getendparam curve-ent)))
  (setq target-pitch (if (= mode "0") dia (- dia overlap))) ; 0: 맞닿음(Tangent), 1: 겹침(Secant)
  
  ;; 폐합 여부에 따라 실제 배치 간격(actual-pitch)을 균등 분배하여 재계산
  (if is-closed
    (progn
      ;; 총 길이를 타겟 간격으로 나누고 반올림(0.5 더한 후 fix)하여 정확한 배치 개수 도출
      (setq count (fix (+ (/ total-length target-pitch) 0.5)))
      ;; 자투리 길이를 분산시킨 완벽한 간격 재계산
      (setq actual-pitch (/ total-length count))
    )
    (progn
      ;; 열린 경계선은 기존의 타겟 간격을 그대로 사용
      (setq actual-pitch target-pitch)
    )
  )
  
  (setq centers '())

  (if is-closed
    (progn
      ;; 닫힌 경계 (Closed boundary)
      (setq dist 0.0)
      (setq i 0)
      ;; 무한 루프나 겹침 초과를 방지하기 위해 계산된 count까지만 배열하도록 조건(< i count) 추가
      (while (and dist (< dist total-length) (< i count))
        (setq pt (vlax-curve-getpointatdist curve-ent dist))
        ;; 꼭짓점 접선각 오류 방지를 위한 미세 보정 (eps = 1e-6)
        (setq check-dist (+ dist 1e-6))
        (if (> check-dist total-length)
          (setq check-dist (- dist 1e-6))
        )
        (setq deriv (vlax-curve-getfirstderiv curve-ent (vlax-curve-getparamatdist curve-ent check-dist)))
        (setq ang (angle '(0 0 0) deriv))
        
        ;; [Phase 1] cons 최적화
        (setq centers (cons (list i dist pt ang) centers))
        
        ;; 다음 C.I.P 중심점 찾기 (균등 분배된 'actual-pitch' 기준 현의 길이 탐색)
        (setq next-dist (tsp-find-next-dist-by-chord curve-ent dist actual-pitch total-length))
        (setq dist next-dist)
        (setq i (1+ i))
      )
      (setq count i)
    )
    (progn
      ;; 열린 경계 (Open boundary)
      (setq dist (/ dia 2.0)) ; 양끝 D/2 보정 적용
      (setq i 0)
      (while (and dist (<= dist (- total-length (/ dia 2.0))))
        (setq pt (vlax-curve-getpointatdist curve-ent dist))
        ;; 꼭짓점 접선각 오류 방지를 위한 미세 보정 (eps = 1e-6)
        (setq check-dist (+ dist 1e-6))
        (if (> check-dist total-length)
          (setq check-dist (- dist 1e-6))
        )
        (setq deriv (vlax-curve-getfirstderiv curve-ent (vlax-curve-getparamatdist curve-ent check-dist)))
        (setq ang (angle '(0 0 0) deriv))
        
        ;; [Phase 1] cons 최적화
        (setq centers (cons (list i dist pt ang) centers))
        
        ;; 다음 C.I.P 중심점 찾기 (열린 구간은 타겟 간격과 동일한 'actual-pitch' 적용)
        (setq next-dist (tsp-find-next-dist-by-chord curve-ent dist actual-pitch total-length))
        (setq dist next-dist)
        (setq i (1+ i))
      )
      (setq count i)
    )
  )

  ;; [Phase 1] 뒤집기 완료
  (setq centers (reverse centers))

  (list
    (cons 'MODE (if is-closed "CLOSED" "OPEN"))
    (cons 'COUNT count)
    (cons 'ACTUAL-PITCH actual-pitch)
    (cons 'ITEMS centers)
  )
)


;;;;==========================================================================
;;;; defun tsp-draw-cip-elements : C.I.P 배열 요소를 작도하고, 브래킷을 생성하는 함수
;;;;==========================================================================
(defun tsp-draw-cip-elements (layout dia interval-idx hpile-idx boundary-orient / interval items hpile-spec-name hpile-vals h b tw tf hpile-block idx dist pt ang outward-normal hpile-rotation insert-pt half-h-offset in-norm p-start-center p-end-center p1 p2 p3 p4 br-layer br-color br-pl hatch-obj mspace doc sa err-eval old-hpannotative old-meas err-hatch)

  (defun draw-bracket-poly (pts layer color / lst ent)
    (setq lst (list '(0 . "LWPOLYLINE") '(100 . "AcDbEntity") '(100 . "AcDbPolyline")
                    (cons 8 layer) (cons 62 color) (cons 90 (length pts)) '(70 . 1)))
    (foreach p pts (setq lst (append lst (list (list 10 (car p) (cadr p))))))
    (setq ent (entmakex lst))
    (if (not ent)
      (progn
        (setq lst (subst (cons 8 (getvar "CLAYER")) (assoc 8 lst) lst))
        (setq ent (entmakex lst))
      )
    )
    ent
  )

  (setq interval (cond ((= interval-idx "1") 2) ((= interval-idx "2") 3) (t 1)))
  (setq items (cdr (assoc 'ITEMS layout)))
  
  (setq hpile-spec-name (nth (atoi hpile-idx) *tsp-std-wall-list*))
  (setq hpile-vals (parse-h-spec hpile-spec-name))
  (setq h (nth 0 hpile-vals) b (nth 1 hpile-vals) tw (nth 2 hpile-vals) tf (nth 3 hpile-vals))
  
  (setq hpile-block (create-hpile-section-block h b tw tf))
  
  (create-layer-if-not-exists "_CIP" "2")
  (setq br-layer "_브래킷(bracket)")
  (setq br-color 8)
  (create-layer-if-not-exists br-layer (itoa br-color))

  (setq doc (vla-get-activedocument (vlax-get-acad-object)))
  (if (= (getvar "CVPORT") 1)
    (setq mspace (vla-get-paperspace doc))
    (setq mspace (vla-get-modelspace doc))
  )

  (foreach item items
    (setq idx (nth 0 item) dist (nth 1 item) pt (nth 2 item) ang (nth 3 item))
    
    (entmake (list '(0 . "CIRCLE") (cons 8 "_CIP") (list 10 (car pt) (cadr pt) 0.0) (cons 40 (/ (if (= (type dia) 'STR) (atof dia) dia) 2.0))))
    
    (if (= (rem idx interval) 0)
      (progn
        (setq outward-normal (+ ang (* boundary-orient (/ pi 2.0))))
        (setq hpile-rotation (+ outward-normal (/ pi 2.0)))
        (setq half-h-offset (/ (if (= (type h) 'STR) (atof h) h) 2.0))
        (setq insert-pt (polar pt outward-normal half-h-offset))
        (entmake (list '(0 . "INSERT") (cons 2 hpile-block) '(8 . "_측면말뚝") (list 10 (car insert-pt) (cadr insert-pt) 0.0) '(41 . 1.0) '(42 . 1.0) '(43 . 1.0) (cons 50 hpile-rotation)))
        
        (setq err-eval (vl-catch-all-apply '> (list dia h)))
        
        (if (not (vl-catch-all-error-p err-eval))
          (if err-eval
            (progn
              ;; 띠장 방향 계산
              (setq in-norm outward-normal) 
              (setq p-start-center (polar pt in-norm (/ h 2.0)))
              (setq p-end-center (polar pt in-norm (/ dia 2.0)))
              (setq p1 (polar p-start-center (+ in-norm (/ pi 2.0)) (/ b 2.0)))
              (setq p2 (polar p-end-center (+ in-norm (/ pi 2.0)) (/ b 2.0)))
              (setq p3 (polar p-end-center (- in-norm (/ pi 2.0)) (/ b 2.0)))
              (setq p4 (polar p-start-center (- in-norm (/ pi 2.0)) (/ b 2.0)))
              
              (setq br-pl (draw-bracket-poly (list p1 p2 p3 p4) br-layer br-color))
              (if br-pl
                (progn
                  (setq old-hpannotative (getvar "HPANNOTATIVE"))
                  (if old-hpannotative (setvar "HPANNOTATIVE" 0))

                  (setq err-hatch (vl-catch-all-apply 'vla-addhatch (list mspace 0 "ANSI31" :vlax-true)))
                  (if (not (vl-catch-all-error-p err-hatch))
                    (progn
                      (setq hatch-obj err-hatch)
                      (vl-catch-all-apply 'vla-put-patternscale (list hatch-obj (if (= (getvar "MEASUREMENT") 0) 400.0 20.0)))
                      (vl-catch-all-apply 'vla-put-layer (list hatch-obj br-layer))
                      (vl-catch-all-apply 'vla-put-color (list hatch-obj br-color))
                      (setq sa (vlax-make-safearray 9 (cons 0 0)))
                      (vlax-safearray-fill sa (list (vlax-ename->vla-object br-pl)))
                      (vl-catch-all-apply 'vla-appendouterloop (list hatch-obj sa))
                      (vl-catch-all-apply 'vla-evaluate (list hatch-obj))
                    )
                  )

                  (if old-hpannotative (setvar "HPANNOTATIVE" old-hpannotative))
                )
              )
            )
          )
        )
      )
    )
  )
  (princ)
)


;;;;==========================================================================
;;;; defun tsp-acos : 아크코사인 함수 (수학 연산 지원)
;;;;==========================================================================
(defun tsp-acos (x)
  (cond
    ((>= x 1.0) 0.0)
    ((<= x -1.0) pi)
    (t (atan (sqrt (- 1.0 (* x x))) x))
  )
)

;;;;==========================================================================
;;;; defun tsp-normalize-angle : 각도를 0 ~ 2pi 사이로 정규화
;;;;==========================================================================
(defun tsp-normalize-angle (a)
  (while (>= a (* 2.0 pi)) (setq a (- a (* 2.0 pi))))
  (while (< a 0.0) (setq a (+ a (* 2.0 pi))))
  a
)

;;;;==========================================================================
;;;; defun tsp-ang-dist : 두 각도의 차이(최단거리) 산출
;;;;==========================================================================
(defun tsp-ang-dist (a b / d)
  (setq d (abs (- a b)))
  (if (> d pi) (- (* 2.0 pi) d) d)
)

;;;;==========================================================================
;;;; defun get-grouting-arc-angles : 그라우팅 원과 CIP 원의 겹침을 잘라내기 위한 시작/끝 각도 산출
;;;;==========================================================================
(defun get-grouting-arc-angles (G C1 C2 R_G R_C out-norm / d1 d2 theta1 theta2 a1 a2 a1A a1B a2A a2B E S diff1A diff1B diff2A diff2B S-out S-E)
  (setq d1 (distance G C1) d2 (distance G C2))
  (setq S nil E nil)
  (if (and (< d2 (+ R_G R_C)) (> d2 (abs (- R_G R_C))))
    (progn
      (setq theta2 (tsp-acos (/ (+ (* R_G R_G) (* d2 d2) (- (* R_C R_C))) (* 2.0 R_G d2))))
      (setq a2 (angle G C2))
      (setq a2A (tsp-normalize-angle (+ a2 theta2)))
      (setq a2B (tsp-normalize-angle (- a2 theta2)))
      (setq diff2A (tsp-ang-dist a2A out-norm))
      (setq diff2B (tsp-ang-dist a2B out-norm))
      (if (< diff2A diff2B) (setq S a2A) (setq S a2B))
    )
  )
  (if (and (< d1 (+ R_G R_C)) (> d1 (abs (- R_G R_C))))
    (progn
      (setq theta1 (tsp-acos (/ (+ (* R_G R_G) (* d1 d1) (- (* R_C R_C))) (* 2.0 R_G d1))))
      (setq a1 (angle G C1))
      (setq a1A (tsp-normalize-angle (+ a1 theta1)))
      (setq a1B (tsp-normalize-angle (- a1 theta1)))
      (setq diff1A (tsp-ang-dist a1A out-norm))
      (setq diff1B (tsp-ang-dist a1B out-norm))
      (if (< diff1A diff1B) (setq E a1A) (setq E a1B))
    )
  )
  (if (and S E)
    (progn
      (setq S-out (tsp-normalize-angle (- out-norm S)))
      (setq S-E (tsp-normalize-angle (- E S)))
      (if (<= S-out S-E)
        (list S E)
        (list E S)
      )
    )
    nil
  )
)

;;;;==========================================================================
;;;; defun tsp-draw-grouting : 지정된 두 CIP 원 사이에 그라우팅 원 및 호(Arc) 작도
;;;;==========================================================================
(defun tsp-draw-grouting (C1 C2 cip-d grouting-dia boundary-orient / G-mid seg-ang G-out-norm R_C G R_G arc-angles)
  (setq G-mid (list (/ (+ (car C1) (car C2)) 2.0) (/ (+ (cadr C1) (cadr C2)) 2.0) 0.0))
  (setq seg-ang (angle C1 C2))
  ;; 부호를 (-)로 변경하여 띠장(굴착면)의 반대편인 배면 방향으로 직각 교차점 산출
  (setq G-out-norm (- seg-ang (* boundary-orient (/ pi 2.0))))
  (setq R_C (/ cip-d 2.0))
  (setq G (polar G-mid G-out-norm R_C))
  (setq R_G (/ grouting-dia 2.0))
  (create-layer-if-not-exists "_그라우팅" "5")
  (setq arc-angles (get-grouting-arc-angles G C1 C2 R_G R_C G-out-norm))
  (if arc-angles
    (entmake (list '(0 . "ARC") (cons 8 "_그라우팅") (cons 62 5) (cons 10 G) (cons 40 R_G) (cons 50 (car arc-angles)) (cons 51 (cadr arc-angles))))
    (entmake (list '(0 . "CIRCLE") (cons 8 "_그라우팅") (cons 62 5) (cons 10 G) (cons 40 R_G)))
  )
  (if (= grouting-dia 600.0)
    (entmake (list '(0 . "CIRCLE") (cons 8 "_그라우팅") (cons 62 5) (cons 10 G) (cons 40 25.0)))
  )
)

;;;;==========================================================================
;;;; defun tsp-draw-cip-plan-per-segment : 세그먼트별 연속 CIP 작도 및 브래킷 통합
;;;;==========================================================================
(defun tsp-draw-cip-plan-per-segment (boundary-ent boundary-orient / is-closed orig-vertices n-verts max-segs seg-idx seg-data seg-wall-type chain-pts j next-data next-type stop-chain end-pt save-dia save-mode save-overlap save-interval save-hpile-idx temp-pl vla-pl test-pt vla-offset-list vla-path d wall-dist out-norm hpile-vals h b cip-ctc max-path-len num-verts k dist-start dist-end start-d end-d effective-len num-intervals actual-dist i curr-dist curr-pt param deriv ang interval hpile-block ins-pt hpile-rot seg-hpile-count doc mspace br-layer br-color num-dia num-h num-b h-scale err-catch p-start-center p-end-center p1 p2 p3 p4 br-pl hatch-obj sa save-equal-divide save-grouting grouting-dia old-offsetgap p-orig-start p-path-0 p-path-1 ang-b-start dist-a-start ang-a-start path-origin-dist p-orig-end end-param p-path-last p-path-prev ang-b-end dist-a-end ang-a-end end-shift path-end-dist full-loop sim-dist sim-count prev-sim-dist chain-end-dist d-wrap next-sim err-over err-under num-gaps dist-list d-acc d-raw-list n-dist-raw n-dist last-raw-d total-error raw-pts wrap-d pt adj-indices idx v pt-prev pt-curr dist-prev next-d next-adj curr-adj wrap-dist prev-cip-pt first-cip-pt pt-on-orig orig-param target-k target-index total-counted-in-list v-idx init-val delta max-anchor-L max-anchor-ang max-anchor-free max-anchor-bond has-anchor cip-wale-spec cip-wale-vals cip-wale-h prev-hpile-raw-dist anchor-raw-dist anchor-d-wrap over-dist end-pt-path end-param-path anchor-pt anchor-out-norm cur-brace next-brace next-seg-real-idx dist-to-start dist-to-end brace-blocked chk-last-b-row chk-b-custom chk-b-dist chk-b-h chk-margin cos-val proj-free proj-bond proj-prot pt-base pt-free-end pt-bond-end pt-h1 pt-h2 pt-h3 pt-h4 pt-anchor-start s-item cur-free cur-bond cur-ang cur-L cur-support-list pt-on-orig-anch orig-param-anch target-k-anch target-index-anch cur-vertex-anch next-vertex-anch)
  
  ;; [보조 함수] 닫힌 폴리라인 강제 생성
  (defun draw-bracket-poly (pts layer color / lst ent)
    (setq lst (list '(0 . "LWPOLYLINE") '(100 . "AcDbEntity") '(100 . "AcDbPolyline")
                    (cons 8 layer) (cons 62 color) (cons 90 (length pts)) '(70 . 1)))
    (foreach p pts (setq lst (append lst (list (list 10 (car p) (cadr p))))))
    (setq ent (entmakex lst))
    (if (not ent)
      (progn
        (setq lst (subst (cons 8 (getvar "CLAYER")) (assoc 8 lst) lst))
        (setq ent (entmakex lst))
      )
    )
    ent
  )

  ;; COM 객체용 공간 및 레이어 설정 (브래킷용)
  (setq doc (vla-get-activedocument (vlax-get-acad-object)))
  (if (= (getvar "CVPORT") 1)
    (setq mspace (vla-get-paperspace doc))
    (setq mspace (vla-get-modelspace doc))
  )
  (setq br-layer "_브래킷(bracket)")
  (setq br-color 8)
  (create-layer-if-not-exists br-layer (itoa br-color))

  (setq is-closed (is-closed-polyline boundary-ent))
  (setq orig-vertices (mapcar '(lambda (s) (cdr (assoc 'V-START s))) *segment-list*))  
  (setq *tsp-actual-drawn-hpiles* 0)
  (if (not is-closed)
    (setq orig-vertices (append orig-vertices (list (cdr (assoc 'V-END (last *segment-list*))))))
  )
  (setq n-verts (length orig-vertices))
  (setq max-segs (if is-closed n-verts (1- n-verts)))
  
  (setq seg-idx 0)
  (while (< seg-idx max-segs)
    (setq seg-data (nth seg-idx *segment-list*))
    (setq seg-wall-type (cdr (assoc 'WALL-TYPE seg-data)))
    
    (if (and (= seg-wall-type "CIP") (cdr (assoc 'IS-DEFINED seg-data)))
      (progn
        ;; 1. 연속된 CIP 세그먼트 찾기 (체인 형성)
        (setq chain-pts (list (nth seg-idx orig-vertices)))
        (setq j (1+ seg-idx))
        (setq stop-chain nil)
        
        (while (and (< j max-segs) (not stop-chain))
          (setq next-data (nth j *segment-list*))
          (setq next-type (cdr (assoc 'WALL-TYPE next-data)))
          (if (and (= next-type "CIP") (cdr (assoc 'IS-DEFINED next-data)))
            (progn
              (setq chain-pts (append chain-pts (list (nth j orig-vertices))))
              (setq j (1+ j))
            )
            (setq stop-chain T)
          )
        )
        ;; 체인의 마지막 끝점 안전하게 추가
        (setq end-pt (nth j orig-vertices))
        (if (not end-pt) (setq end-pt (nth 0 orig-vertices)))
        (setq chain-pts (append chain-pts (list end-pt)))
        
        ;; 2. 세그먼트 파라미터 로드
        (setq save-dia *tsp-cip-dia*
              save-mode *tsp-cip-mode-idx*
              save-overlap *tsp-cip-overlap*
              save-equal-divide *tsp-cip-equal-divide*
              save-interval *tsp-cip-interval-idx*
              save-hpile-idx *tsp-cip-hpile-idx*
              save-grouting *tsp-cip-grouting-idx*)
        (setq *tsp-cip-dia* (cdr (assoc 'CIP-DIA seg-data)))
        (setq *tsp-cip-mode-idx* (cdr (assoc 'CIP-MODE-IDX seg-data)))
        (setq *tsp-cip-overlap* (cdr (assoc 'CIP-OVERLAP seg-data)))
        (setq *tsp-cip-equal-divide* (if (assoc 'CIP-EQUAL-DIVIDE seg-data) (cdr (assoc 'CIP-EQUAL-DIVIDE seg-data)) "0"))
        (setq *tsp-cip-interval-idx* (cdr (assoc 'CIP-INTERVAL-IDX seg-data)))
        (setq *tsp-cip-hpile-idx* (cdr (assoc 'CIP-HPILE-IDX seg-data)))
        (setq *tsp-cip-grouting-idx* (cdr (assoc 'CIP-GROUTING-IDX seg-data)))
        (setq grouting-dia (if (= *tsp-cip-grouting-idx* "1") 600.0 200.0))
        
        (setq d (atof *tsp-cip-dia*))
        (setq wall-dist (/ d 2.0))
        (setq cip-ctc (if (= *tsp-cip-mode-idx* "0") d (- d (atof *tsp-cip-overlap*))))
        (setq hpile-vals (parse-h-spec (nth (atoi *tsp-cip-hpile-idx*) *tsp-std-wall-list*)))
        (setq h (nth 0 hpile-vals) b (nth 1 hpile-vals))
        (setq hpile-block (create-hpile-section-block h b (nth 2 hpile-vals) (nth 3 hpile-vals)))
        (setq interval (cond ((= *tsp-cip-interval-idx* "1") 2) ((= *tsp-cip-interval-idx* "2") 3) (t 1)))

        ;; 3. 임시 연속 폴리선 생성 및 오프셋
        (setq temp-pl (entmakex (append (list '(0 . "LWPOLYLINE") '(100 . "AcDbEntity") '(100 . "AcDbPolyline") 
                                              (cons 90 (length chain-pts)) '(70 . 0))
                                        (mapcar '(lambda (p) (list 10 (car p) (cadr p))) chain-pts))))
        (setq vla-pl (vlax-ename->vla-object temp-pl))
        
        (setq out-norm (+ (angle (nth 0 chain-pts) (nth 1 chain-pts)) (* boundary-orient (/ pi 2.0))))
        (setq test-pt (polar (nth 0 chain-pts) out-norm (- wall-dist)))
        
        (setq old-offsetgap (getvar "OFFSETGAPTYPE"))
        (setvar "OFFSETGAPTYPE" 1)

        (setq vla-offset-list (vl-catch-all-apply 'vla-offset (list vla-pl wall-dist)))
        (if (not (vl-catch-all-error-p vla-offset-list))
          (progn
            (setq vla-path (vlax-safearray-get-element (vlax-variant-value vla-offset-list) 0))
            (if (> (distance (list (car test-pt) (cadr test-pt)) 
                             (list (car (vlax-curve-getStartPoint vla-path)) (cadr (vlax-curve-getStartPoint vla-path)))) 0.1)
              (progn
                (vla-delete vla-path)
                (setq vla-path (vlax-safearray-get-element (vlax-variant-value (vla-offset vla-pl (- wall-dist))) 0))
              )
            )
            (setvar "OFFSETGAPTYPE" old-offsetgap)
            
            ;; 4. 연속 선형 기반 CIP 및 H-Pile 배열
            (setq max-path-len (vlax-curve-getdistatparam vla-path (vlax-curve-getendparam vla-path)))
            (setq num-verts (1+ (fix (vlax-curve-getendparam vla-path))))
            (create-layer-if-not-exists "_CIP" "2")
            
            (setq k 0)
            (while (< k (- num-verts 1))
              (setq init-val (if (and (= seg-idx 0) (= k 0)) 1 0))
              (setq *tsp-segment-pile-counts* (update-list-item *tsp-segment-pile-counts* (+ seg-idx k) init-val))
              (setq k (1+ k))
            )
            
            ;; 오프셋 보정
            (setq p-orig-start (nth 0 chain-pts))
            (setq p-path-0 (vlax-curve-getPointAtParam vla-path 0.0))
            (setq p-path-1 (vlax-curve-getPointAtParam vla-path 1.0))
            
            (setq ang-b-start (angle p-path-0 p-path-1))
            (setq dist-a-start (distance p-path-0 p-orig-start))
            (setq ang-a-start (angle p-path-0 p-orig-start))
            
            (setq path-origin-dist (* dist-a-start (cos (- ang-a-start ang-b-start))))
            (if (< path-origin-dist 0.0) (setq path-origin-dist 0.0))
            
            (setq start-d (+ path-origin-dist (/ b 2.0)))

            (setq p-orig-end (last chain-pts))
            (setq end-param (vlax-curve-getEndParam vla-path))
            (setq p-path-last (vlax-curve-getPointAtParam vla-path end-param))
            (setq p-path-prev (vlax-curve-getPointAtParam vla-path (1- end-param)))
            
            (setq ang-b-end (angle p-path-prev p-path-last))
            (setq dist-a-end (distance p-path-last p-orig-end))
            (setq ang-a-end (angle p-path-last p-orig-end))
            
            (setq end-shift (* dist-a-end (cos (- ang-a-end (+ ang-b-end pi)))))
            (if (< end-shift 0.0) (setq end-shift 0.0))
            
            (setq path-end-dist (- max-path-len end-shift))
            (setq end-d (- path-end-dist (/ b 2.0)))
            
            (if (<= end-d start-d)
              (progn
                (setq start-d (/ b 2.0))
                (setq end-d (- max-path-len (/ b 2.0)))
              )
            )
            
            (setq effective-len (- end-d start-d))
            
            (setq full-loop (and is-closed (= (length chain-pts) (1+ max-segs))))
            (if full-loop
              (progn
                (setq effective-len max-path-len)
                (setq end-d (+ start-d max-path-len))
              )
            )
            
            (defun get-robust-chord-inc (path start-wrap chord-len max-len is-closed / p1 low high b-iter mid wrap-test p2-catch d-test)
              (setq p1 (vlax-curve-getpointatdist path start-wrap))
              (setq low chord-len high (* chord-len 1.5))
              (setq b-iter 0)
              (while (< b-iter 15)
                (setq mid (/ (+ low high) 2.0))
                (setq wrap-test (+ start-wrap mid))
                (if (and is-closed (> max-len 0.0)) (while (>= wrap-test max-len) (setq wrap-test (- wrap-test max-len))))
                (setq p2-catch (vl-catch-all-apply 'vlax-curve-getpointatdist (list path wrap-test)))
                (if (or (vl-catch-all-error-p p2-catch) (not p2-catch))
                  (setq high mid)
                  (progn
                    (setq d-test (distance (list (car p1) (cadr p1)) (list (car p2-catch) (cadr p2-catch))))
                    (if (< d-test chord-len) (setq low mid) (setq high mid))
                  )
                )
                (setq b-iter (1+ b-iter))
              )
              mid
            )

            (setq sim-dist start-d)
            (setq sim-count 0)
            (setq prev-sim-dist start-d)
            (setq chain-end-dist (if full-loop (+ start-d max-path-len) max-path-len))
            (while (< sim-dist chain-end-dist)
              (setq prev-sim-dist sim-dist)
              (setq d-wrap sim-dist)
              (if (> max-path-len 0.0) (while (>= d-wrap max-path-len) (setq d-wrap (- d-wrap max-path-len))))
              (setq next-sim (tsp-find-next-dist-by-chord vla-path d-wrap cip-ctc max-path-len))
              (if next-sim
                (setq sim-dist (+ sim-dist (- next-sim d-wrap)))
                (setq sim-dist (+ sim-dist (get-robust-chord-inc vla-path d-wrap cip-ctc max-path-len full-loop)))
              )
              (setq sim-count (1+ sim-count))
            )
            (setq err-over (- sim-dist chain-end-dist))
            (setq err-under (- chain-end-dist prev-sim-dist))
            (if (< err-under err-over)
              (setq num-gaps (1- sim-count))
              (setq num-gaps sim-count)
            )
            (if (< num-gaps 1) (setq num-gaps 1))
            
            (setq dist-list '())
            (setq chain-end-dist (if full-loop (+ start-d max-path-len) max-path-len))
            (setq d-acc start-d)
            (setq d-raw-list (list d-acc))
            
            (if full-loop
              (progn
                (while (< d-acc chain-end-dist)
                  (setq d-wrap d-acc)
                  (if (> max-path-len 0.0) (while (>= d-wrap max-path-len) (setq d-wrap (- d-wrap max-path-len))))
                  (setq n-dist-raw (tsp-find-next-dist-by-chord vla-path d-wrap cip-ctc max-path-len))
                  (if n-dist-raw
                    (setq n-dist (+ d-acc (- n-dist-raw d-wrap)))
                    (setq n-dist (+ d-acc (get-robust-chord-inc vla-path d-wrap cip-ctc max-path-len full-loop)))
                  )
                  (setq d-raw-list (append d-raw-list (list n-dist)))
                  (setq d-acc n-dist)
                )
                
                (setq last-raw-d (last d-raw-list))
                (setq total-error (- last-raw-d chain-end-dist))

                (setq raw-pts '())
                (foreach d-val d-raw-list
                  (setq wrap-d d-val)
                  (if (> max-path-len 0.0) (while (>= wrap-d max-path-len) (setq wrap-d (- wrap-d max-path-len))))
                  (if (< wrap-d 0.0) (setq wrap-d 0.0))
                  (setq pt (vlax-curve-getpointatdist vla-path wrap-d))
                  (setq raw-pts (append raw-pts (list pt)))
                )
                
                (setq adj-indices '())
                (foreach v orig-vertices
                  (setq idx 1)
                  (while (< idx (length raw-pts))
                    (setq pt-prev (nth (1- idx) raw-pts))
                    (setq pt-curr (nth idx raw-pts))
                    
                    (setq dist-prev (distance (list (car pt-prev) (cadr pt-prev)) (list (car v) (cadr v))))
                    (setq dist-curr (distance (list (car pt-curr) (cadr pt-curr)) (list (car v) (cadr v))))
                    
                    (if (and (<= dist-prev (+ d 1.0)) (<= dist-curr (+ d 1.0)))
                      (if (not (member idx adj-indices))
                        (setq adj-indices (append adj-indices (list idx)))
                      )
                    )
                    (setq idx (1+ idx))
                  )
                )

                (if (= (length adj-indices) 0)
                  (progn
                    (setq idx 1)
                    (while (< idx (length d-raw-list))
                      (setq adj-indices (append adj-indices (list idx)))
                      (setq idx (1+ idx))
                    )
                  )
                )

                (setq delta (/ total-error (float (length adj-indices))))
                
                (setq dist-list (list start-d))
                (setq curr-adj start-d)
                (setq idx 1)
                (while (< idx (length d-raw-list))
                  (setq d-wrap curr-adj)
                  (if (> max-path-len 0.0) (while (>= d-wrap max-path-len) (setq d-wrap (- d-wrap max-path-len))))
                  (setq n-dist-raw (tsp-find-next-dist-by-chord vla-path d-wrap cip-ctc max-path-len))
                  
                  (if n-dist-raw
                    (setq next-d (+ curr-adj (- n-dist-raw d-wrap)))
                    (setq next-d (+ curr-adj (get-robust-chord-inc vla-path d-wrap cip-ctc max-path-len full-loop)))
                  )
                  
                  (if (member idx adj-indices)
                    (setq next-adj (- next-d delta))
                    (setq next-adj next-d)
                  )
                  
                  (setq curr-adj next-adj)
                  (setq dist-list (append dist-list (list curr-adj)))
                  (setq idx (1+ idx))
                )
                
                (setq dist-list (reverse (cdr (reverse dist-list))))
                (setq dist-list (append dist-list (list chain-end-dist)))
              )
              (progn
                (while (< (+ d-acc wall-dist) chain-end-dist)
                  (setq d-wrap d-acc)
                  (setq n-dist-raw (tsp-find-next-dist-by-chord vla-path d-wrap cip-ctc max-path-len))
                  (if n-dist-raw
                    (setq n-dist (+ d-acc (- n-dist-raw d-wrap)))
                    (setq n-dist (+ d-acc (get-robust-chord-inc vla-path d-wrap cip-ctc max-path-len nil)))
                  )
                  (setq d-raw-list (append d-raw-list (list n-dist)))
                  (setq d-acc n-dist)
                )
                (setq dist-list d-raw-list)
              )
            )
            (setq num-gaps (1- (length dist-list)))

            ;; [2] 통합 작도 실행 루프 (앵커 포함)
            (setq i 0)
            (setq prev-cip-pt nil first-cip-pt nil)
            (setq prev-hpile-raw-dist nil)
            
            (foreach wrap-raw dist-list
              (setq wrap-dist wrap-raw)
              
              (if (and full-loop (> max-path-len 0.0))
                (while (>= wrap-dist max-path-len) (setq wrap-dist (- wrap-dist max-path-len)))
              )
              (if (< wrap-dist 0.0) (setq wrap-dist 0.0))

              (if (not (and full-loop (= i num-gaps)))
                (progn
                  (if (> wrap-dist max-path-len)
                    (progn
                      (setq over-dist (- wrap-dist max-path-len))
                      (setq end-pt-path (vlax-curve-getpointatdist vla-path max-path-len))
                      (setq end-param-path (vlax-curve-getendparam vla-path))
                      (setq deriv (vlax-curve-getfirstderiv vla-path end-param-path))
                      (setq ang (atan (cadr deriv) (car deriv)))
                      (setq curr-pt (polar end-pt-path ang over-dist))
                    )
                    (progn
                      (setq curr-pt (vlax-curve-getpointatdist vla-path wrap-dist))
                      (setq param (vlax-curve-getparamatdist vla-path wrap-dist))
                      (setq deriv (vlax-curve-getfirstderiv vla-path param))
                      (setq ang (atan (cadr deriv) (car deriv)))
                    )
                  )
                  
                  (setq pt-on-orig (vlax-curve-getClosestPointTo vla-pl curr-pt))
                  (setq orig-param (vlax-curve-getParamAtPoint vla-pl pt-on-orig))
                  (setq target-k (fix orig-param))
                  (if (>= target-k (1- (length chain-pts))) (setq target-k (- (length chain-pts) 2)))
                  (setq out-norm (+ ang (* boundary-orient (/ pi 2.0))))
                  (setq hpile-rot (+ out-norm (/ pi 2.0)))
                  (setq ins-pt (polar curr-pt out-norm (/ h 2.0)))

                  ;; [1] CIP 원형 작성
                  (entmake (list '(0 . "CIRCLE") (cons 8 "_CIP") (list 10 (car curr-pt) (cadr curr-pt) 0.0) (cons 40 (/ d 2.0))))

                  ;; [2] H-Pile 작성 및 앵커/브래킷 생성
                  (if (= (rem i interval) 0)
                    (progn
                      (entmake (list '(0 . "INSERT") (cons 2 hpile-block) '(8 . "_측면말뚝") (list 10 (car ins-pt) (cadr ins-pt) 0.0) '(41 . 1.0) '(42 . 1.0) '(43 . 1.0) (cons 50 hpile-rot)))
                      (setq *tsp-hpile-points* (append *tsp-hpile-points* (list (list (car ins-pt) (cadr ins-pt) 0.0))))
                      
                      ;; [2.1] 브래킷 및 해치 작도
                      (setq num-dia (if (= (type d) 'STR) (atof d) d))
                      (setq num-h (if (= (type h) 'STR) (atof h) h))
                      (setq num-b (if (= (type b) 'STR) (atof b) b))
                      (if (> num-dia num-h)
                        (progn
                          (setq p-start-center (polar curr-pt out-norm (/ num-h 2.0)))
                          (setq p-end-center (polar curr-pt out-norm (/ num-dia 2.0)))
                          (setq p1 (polar p-start-center (+ out-norm (/ pi 2.0)) (/ num-b 2.0)))
                          (setq p2 (polar p-end-center (+ out-norm (/ pi 2.0)) (/ num-b 2.0)))
                          (setq p3 (polar p-end-center (- out-norm (/ pi 2.0)) (/ num-b 2.0)))
                          (setq p4 (polar p-start-center (- out-norm (/ pi 2.0)) (/ num-b 2.0)))
                          (setq br-pl (draw-bracket-poly (list p1 p2 p3 p4) br-layer br-color))
                          (if br-pl
                            (progn
                              (setq err-catch (vl-catch-all-apply 'vla-addhatch (list mspace 0 "ANSI31" :vlax-true)))
                              (if (not (vl-catch-all-error-p err-catch))
                                (progn
                                  (setq hatch-obj err-catch)
                                  (setq sa (vlax-make-safearray 9 (cons 0 0)))
                                  (vlax-safearray-fill sa (list (vlax-ename->vla-object br-pl)))
                                  (vla-appendouterloop hatch-obj sa)
                                  (vla-evaluate hatch-obj)
                                  (vla-put-patternscale hatch-obj (if (= (getvar "MEASUREMENT") 0) 400.0 20.0))
                                  (vla-put-layer hatch-obj br-layer)
                                  (vla-put-color hatch-obj br-color)
                                )
                              )
                            )
                          )
                        )
                      )

                      ;; [2.2] 앵커 작도
                      ;; 껍데기 가드를 무력화(T)하여, 항상 내부로 진입한 뒤 세그먼트별로 앵커 여부를 동적 판별하도록 변경
                      (if T
                        (if prev-hpile-raw-dist
                          (progn
                            (if (= interval 2)
                              (setq anchor-raw-dist (+ prev-hpile-raw-dist (/ (- wrap-raw prev-hpile-raw-dist) 4.0)))
                              (setq anchor-raw-dist (/ (+ prev-hpile-raw-dist wrap-raw) 2.0))
                            )
                            (setq anchor-d-wrap anchor-raw-dist)
                            (if (and full-loop (> max-path-len 0.0))
                              (while (>= anchor-d-wrap max-path-len) (setq anchor-d-wrap (- anchor-d-wrap max-path-len)))
                            )
                            (if (> anchor-d-wrap max-path-len)
                              (progn
                                (setq over-dist (- anchor-d-wrap max-path-len))
                                (setq end-pt-path (vlax-curve-getpointatdist vla-path max-path-len))
                                (setq end-param-path (vlax-curve-getendparam vla-path))
                                (setq deriv (vlax-curve-getfirstderiv vla-path end-param-path))
                                (setq ang (atan (cadr deriv) (car deriv)))
                                (setq anchor-pt (polar end-pt-path ang over-dist))
                              )
                              (progn
                                (setq anchor-pt (vlax-curve-getpointatdist vla-path anchor-d-wrap))
                                (setq param (vlax-curve-getparamatdist vla-path anchor-d-wrap))
                                (setq deriv (vlax-curve-getfirstderiv vla-path param))
                                (setq ang (atan (cadr deriv) (car deriv)))
                              )
                            )
                            (setq anchor-out-norm (+ ang (* boundary-orient (/ pi 2.0))))

                            ;; 사보강재 간섭 체크
                            ;; CIP가 여러 세그먼트로 체인 연결되었을 때, 앵커가 속한 '현재 하위 세그먼트'를 정확히 추적하여 모서리 간섭 판별
                            (setq pt-on-orig-anch (vlax-curve-getClosestPointTo vla-pl anchor-pt))
                            (setq orig-param-anch (vlax-curve-getParamAtPoint vla-pl pt-on-orig-anch))
                            (setq target-k-anch (fix orig-param-anch))
                            (if (>= target-k-anch (1- (length chain-pts))) (setq target-k-anch (- (length chain-pts) 2)))
                            
                            (setq target-index-anch (+ seg-idx target-k-anch))
                            (if (and is-closed (>= target-index-anch max-segs)) (setq target-index-anch (rem target-index-anch max-segs)))
                            
                            ;; 앵커 데이터 동적 파싱 (체인으로 묶인 각 세그먼트의 고유 지보재 데이터 적용)
                            (setq max-anchor-L 0.0 max-anchor-ang 0.0 max-anchor-free 0.0 max-anchor-bond 0.0 has-anchor nil)
                            (setq cur-support-list (cdr (assoc 'SUPPORT-LIST (nth target-index-anch *segment-list*))))
                            (if cur-support-list
                              (foreach s-item cur-support-list
                                (if (wcmatch (car s-item) "*앵커*")
                                  (progn
                                    (setq cur-free (nth 5 s-item) cur-bond (nth 6 s-item) cur-ang (nth 4 s-item))
                                    (setq cur-L (+ cur-free cur-bond))
                                    (if (> cur-L max-anchor-L) 
                                      (setq max-anchor-L cur-L max-anchor-ang cur-ang max-anchor-free cur-free max-anchor-bond cur-bond has-anchor T)
                                    )
                                  )
                                )
                              )
                            )
                            
                            ;; 띠장(Wale) 제원 동적 파싱 (앵커 시작점 오프셋 계산용)
                            (setq cip-wale-spec (cdr (assoc 'WALE-SPEC (nth target-index-anch *segment-list*))))
                            (if (= cip-wale-spec "User-defined") 
                              (setq cip-wale-vals (cdr (assoc 'WALE-CUSTOM (nth target-index-anch *segment-list*)))) 
                              (setq cip-wale-vals (parse-h-spec cip-wale-spec))
                            )
                            (if (null cip-wale-vals) (setq cip-wale-vals '(300 300 10 15)))
                            (setq cip-wale-h (nth 0 cip-wale-vals))

                            (setq cur-brace (cdr (assoc 'CORNER-BRACE (nth target-index-anch *segment-list*))))
                            (setq next-seg-real-idx (if is-closed (rem (+ target-index-anch 1) n-verts) (+ target-index-anch 1)))
                            (setq next-brace nil)
                            (if (and next-seg-real-idx (< next-seg-real-idx (length *segment-list*)))
                              (setq next-brace (cdr (assoc 'CORNER-BRACE (nth next-seg-real-idx *segment-list*))))
                            )
                            
                            (setq cur-vertex-anch (nth target-k-anch chain-pts))
                            (setq next-vertex-anch (nth (1+ target-k-anch) chain-pts))
                            (setq dist-to-start (distance (list (car cur-vertex-anch) (cadr cur-vertex-anch)) (list (car pt-on-orig-anch) (cadr pt-on-orig-anch))))
                            (setq dist-to-end (distance (list (car next-vertex-anch) (cadr next-vertex-anch)) (list (car pt-on-orig-anch) (cadr pt-on-orig-anch))))
                            (setq brace-blocked nil)

                            ;; C.I.P 상향 띠장(Upgraded Wale) 구역을 포함한 사보강재/앵커 간섭 정밀 체크 (실제 dist-list 탐색 적용)
                            (setq c-upg-s (cdr (assoc 'UPGRADE-WALE (nth target-index-anch *segment-list*))))
                            (setq has-upg-s (and c-upg-s (= (car c-upg-s) "Y")))
                            (setq c-upg-e (cdr (assoc 'UPGRADE-WALE (nth next-seg-real-idx *segment-list*))))
                            (setq has-upg-e (and c-upg-e (= (car c-upg-e) "Y")))
                            (setq base-clear 500.0)
                            (setq min-limit-s base-clear min-limit-e base-clear)
                            (setq upg-center-s 0.0 upg-center-e 0.0)
                            (setq exact-L-start base-clear exact-L-end base-clear)
                            
                            (if (and cur-brace (= (car cur-brace) "Y") (cadr cur-brace))
                              (progn
                                (setq chk-last-b-row (last (cadr cur-brace)))
                                (setq chk-b-h (nth 0 (cadr chk-last-b-row)))
                                (setq chk-edge (if (wcmatch (strcase (nth 0 chk-last-b-row)) "2H*") (* chk-b-h 1.5) (/ chk-b-h 2.0)))
                                (setq min-limit-s (max base-clear (+ (* (nth 2 chk-last-b-row) 1000.0) chk-edge 150.0)))
                                (setq exact-L-start min-limit-s)
                              )
                            )
                            (if has-upg-s
                              (progn
                                (setq best-d 1e99 k 0)
                                (foreach d-val dist-list
                                  (if (= (rem k interval) 0)
                                    (progn
                                      (setq d-wrap d-val)
                                      (if (and full-loop (> max-path-len 0.0))
                                        (while (>= d-wrap max-path-len) (setq d-wrap (- d-wrap max-path-len))))
                                      (if (< d-wrap 0.0) (setq d-wrap 0.0))
                                      (if (> d-wrap max-path-len)
                                        (progn
                                          (setq end-pt-path (vlax-curve-getpointatdist vla-path max-path-len))
                                          (setq end-param-path (vlax-curve-getendparam vla-path))
                                          (setq deriv (vlax-curve-getfirstderiv vla-path end-param-path))
                                          (setq ang (atan (cadr deriv) (car deriv)))
                                          (setq p-temp (polar end-pt-path ang (- d-wrap max-path-len)))
                                        )
                                        (setq p-temp (vlax-curve-getpointatdist vla-path d-wrap))
                                      )
                                      (setq p-on-orig (vlax-curve-getClosestPointTo vla-pl p-temp))
                                      (setq p-param (vlax-curve-getParamAtPoint vla-pl p-on-orig))
                                      (if (and (>= p-param target-k-anch) (<= p-param (1+ target-k-anch)))
                                        (progn
                                          (setq d-dist (distance (list (car cur-vertex-anch) (cadr cur-vertex-anch)) (list (car p-on-orig) (cadr p-on-orig))))
                                          (if (> (+ d-dist 150.0) min-limit-s)
                                            (if (< d-dist best-d) (setq best-d d-dist))
                                          )
                                        )
                                      )
                                    )
                                  )
                                  (setq k (1+ k))
                                )
                                (if (< best-d 1e90)
                                  (progn
                                    (setq upg-center-s best-d)
                                    (setq exact-L-start (max exact-L-start (+ best-d 150.0)))
                                  )
                                )
                              )
                            )
                            
                            (if (and next-brace (= (car next-brace) "Y") (cadr next-brace))
                              (progn
                                (setq chk-last-b-row (last (cadr next-brace)))
                                (setq chk-b-h (nth 0 (cadr chk-last-b-row)))
                                (setq chk-edge (if (wcmatch (strcase (nth 0 chk-last-b-row)) "2H*") (* chk-b-h 1.5) (/ chk-b-h 2.0)))
                                (setq min-limit-e (max base-clear (+ (* (nth 2 chk-last-b-row) 1000.0) chk-edge 150.0)))
                                (setq exact-L-end min-limit-e)
                              )
                            )
                            (if has-upg-e
                              (progn
                                (setq best-d 1e99 k 0)
                                (foreach d-val dist-list
                                  (if (= (rem k interval) 0)
                                    (progn
                                      (setq d-wrap d-val)
                                      (if (and full-loop (> max-path-len 0.0))
                                        (while (>= d-wrap max-path-len) (setq d-wrap (- d-wrap max-path-len))))
                                      (if (< d-wrap 0.0) (setq d-wrap 0.0))
                                      (if (> d-wrap max-path-len)
                                        (progn
                                          (setq end-pt-path (vlax-curve-getpointatdist vla-path max-path-len))
                                          (setq end-param-path (vlax-curve-getendparam vla-path))
                                          (setq deriv (vlax-curve-getfirstderiv vla-path end-param-path))
                                          (setq ang (atan (cadr deriv) (car deriv)))
                                          (setq p-temp (polar end-pt-path ang (- d-wrap max-path-len)))
                                        )
                                        (setq p-temp (vlax-curve-getpointatdist vla-path d-wrap))
                                      )
                                      (setq p-on-orig (vlax-curve-getClosestPointTo vla-pl p-temp))
                                      (setq p-param (vlax-curve-getParamAtPoint vla-pl p-on-orig))
                                      (if (and (>= p-param target-k-anch) (<= p-param (1+ target-k-anch)))
                                        (progn
                                          (setq d-dist (distance (list (car next-vertex-anch) (cadr next-vertex-anch)) (list (car p-on-orig) (cadr p-on-orig))))
                                          (if (> (+ d-dist 150.0) min-limit-e)
                                            (if (< d-dist best-d) (setq best-d d-dist))
                                          )
                                        )
                                      )
                                    )
                                  )
                                  (setq k (1+ k))
                                )
                                (if (< best-d 1e90)
                                  (progn
                                    (setq upg-center-e best-d)
                                    (setq exact-L-end (max exact-L-end (+ best-d 150.0)))
                                  )
                                )
                              )
                            )
                            
                            (if (and next-brace (= (car next-brace) "Y") (cadr next-brace))
                              (progn
                                (setq chk-last-b-row (last (cadr next-brace)))
                                (setq min-limit-e (+ (* (nth 2 chk-last-b-row) 1000.0) (/ (nth 0 (cadr chk-last-b-row)) 2.0) 150.0))
                                (setq exact-L-end min-limit-e)
                              )
                            )
                            (if has-upg-e
                              (progn
                                (setq best-d 1e99 k 0)
                                (foreach d-val dist-list
                                  (if (= (rem k interval) 0)
                                    (progn
                                      (setq d-wrap d-val)
                                      (if (and full-loop (> max-path-len 0.0))
                                        (while (>= d-wrap max-path-len) (setq d-wrap (- d-wrap max-path-len))))
                                      (if (< d-wrap 0.0) (setq d-wrap 0.0))
                                      (if (> d-wrap max-path-len)
                                        (progn
                                          (setq end-pt-path (vlax-curve-getpointatdist vla-path max-path-len))
                                          (setq end-param-path (vlax-curve-getendparam vla-path))
                                          (setq deriv (vlax-curve-getfirstderiv vla-path end-param-path))
                                          (setq ang (atan (cadr deriv) (car deriv)))
                                          (setq p-temp (polar end-pt-path ang (- d-wrap max-path-len)))
                                        )
                                        (setq p-temp (vlax-curve-getpointatdist vla-path d-wrap))
                                      )
                                      (setq p-on-orig (vlax-curve-getClosestPointTo vla-pl p-temp))
                                      (setq p-param (vlax-curve-getParamAtPoint vla-pl p-on-orig))
                                      (if (and (>= p-param target-k-anch) (<= p-param (1+ target-k-anch)))
                                        (progn
                                          (setq d-dist (distance (list (car next-vertex-anch) (cadr next-vertex-anch)) (list (car p-on-orig) (cadr p-on-orig))))
                                          (if (> (+ d-dist 150.0) min-limit-e)
                                            (if (< d-dist best-d) (setq best-d d-dist))
                                          )
                                        )
                                      )
                                    )
                                  )
                                  (setq k (1+ k))
                                )
                                (if (< best-d 1e90)
                                  (progn
                                    (setq upg-center-e best-d)
                                    (setq exact-L-end (+ best-d 150.0))
                                  )
                                )
                              )
                            )
                            
                            ;; 세그먼트 전체 길이 계산
                            (setq sub-seg-len (distance (list (car cur-vertex-anch) (cadr cur-vertex-anch)) (list (car next-vertex-anch) (cadr next-vertex-anch))))
                            
                            ;; CTC 기준 전체 상향(Full Upgrade) 검사 - 띠장 로직과 완벽 동기화 (중심점 기준)
                            (setq check-L-s (if has-upg-s upg-center-s 0.0))
                            (setq check-L-e (if has-upg-e upg-center-e 0.0))
                            
                            (if (and (or (> check-L-s 0.0) (> check-L-e 0.0))
                                     (< (- sub-seg-len (+ check-L-s check-L-e)) (* cip-ctc interval 1.5)))
                              (setq exact-L-start sub-seg-len exact-L-end sub-seg-len)
                            )
                            
                            ;; 최종 간섭 판별 (상향 띠장 구간 내에는 앵커 배치 불가)
                            (if (or (<= dist-to-start exact-L-start) (<= dist-to-end exact-L-end))
                              (setq brace-blocked T)
                            )

                            ;; 해당 세그먼트에 앵커가 존재(has-anchor)할 때만 작도하도록 조건 추가
                            (if (and has-anchor (not brace-blocked))
                              (progn
                                (create-layer-if-not-exists "_앵커(Anchor)" "6")
                                (setq cos-val (cos (* max-anchor-ang (/ pi 180.0))))
                                (setq proj-free (* max-anchor-free 1000.0 cos-val) proj-bond (* max-anchor-bond 1000.0 cos-val) proj-prot (* 150.0 cos-val))
                                
                                (setq pt-base (polar anchor-pt anchor-out-norm (+ (/ d 2.0) cip-wale-h)))
                                
                                (setq pt-free-end (polar pt-base (+ anchor-out-norm pi) proj-free) pt-bond-end (polar pt-free-end (+ anchor-out-norm pi) proj-bond))
                                (setq pt-h1 (polar pt-base (+ anchor-out-norm (/ pi 2.0)) 100.0) pt-h2 (polar pt-base (- anchor-out-norm (/ pi 2.0)) 100.0))
                                (setq pt-h3 (polar pt-h2 anchor-out-norm 60.0) pt-h4 (polar pt-h1 anchor-out-norm 60.0))
                                
                                (entmake (list '(0 . "LWPOLYLINE") '(100 . "AcDbEntity") '(100 . "AcDbPolyline") (cons 8 "_앵커(Anchor)") (cons 62 6) '(90 . 4) '(70 . 1) (list 10 (car pt-h1) (cadr pt-h1)) (list 10 (car pt-h2) (cadr pt-h2)) (list 10 (car pt-h3) (cadr pt-h3)) (list 10 (car pt-h4) (cadr pt-h4))))
                                (setq pt-anchor-start (polar pt-base anchor-out-norm (+ 60.0 proj-prot)))
                                
                                (entmake (list '(0 . "LWPOLYLINE") '(100 . "AcDbEntity") '(100 . "AcDbPolyline") (cons 8 "_앵커(Anchor)") (cons 62 6) '(90 . 2) '(70 . 0) (list 10 (car pt-anchor-start) (cadr pt-anchor-start)) (list 10 (car pt-base) (cadr pt-base))))
                                (entmake (list '(0 . "LWPOLYLINE") '(100 . "AcDbEntity") '(100 . "AcDbPolyline") (cons 8 "_앵커(Anchor)") (cons 62 6) '(90 . 2) '(70 . 0) (list 10 (car pt-base) (cadr pt-base)) (list 10 (car pt-free-end) (cadr pt-free-end))))
                                (entmake (list '(0 . "LWPOLYLINE") '(100 . "AcDbEntity") '(100 . "AcDbPolyline") (cons 8 "_앵커(Anchor)") (cons 62 6) '(90 . 2) '(70 . 0) '(43 . 400.0) (list 10 (car pt-free-end) (cadr pt-free-end)) (list 10 (car pt-bond-end) (cadr pt-bond-end))))
                              )
                            )
                          )
                        )
                      )

                      ;; H-Pile 개수 카운팅
                      (setq target-index (+ seg-idx target-k))
                      (if (and is-closed (>= target-index (length *segment-list*))) (setq target-index 0))
                      (setq seg-hpile-count (nth target-index *tsp-segment-pile-counts*))
                      (if (null seg-hpile-count) (setq seg-hpile-count 0))
                      (if (and (= target-index 0) (= seg-hpile-count 1) (= i 0))
                        nil
                        (setq *tsp-segment-pile-counts* (update-list-item *tsp-segment-pile-counts* target-index (1+ seg-hpile-count)))
                      )
                      (setq *tsp-actual-drawn-hpiles* (1+ *tsp-actual-drawn-hpiles*))
                      
                      ;; [2.3] 현재 H-Pile 위치 저장 (다음 앵커 생성을 위함)
                      (setq prev-hpile-raw-dist wrap-raw)
                    )
                  )
                  
                  ;; [2.5] 그라우팅 작성
                  (if (= i 0) (setq first-cip-pt curr-pt))
                  (if prev-cip-pt (tsp-draw-grouting prev-cip-pt curr-pt d grouting-dia boundary-orient))
                  (setq prev-cip-pt curr-pt)
                )
                (progn
                  ;; 마지막 노드 폐합 마감 (그라우팅 연결)
                  (if prev-cip-pt (tsp-draw-grouting prev-cip-pt first-cip-pt d grouting-dia boundary-orient))
                )
              )
              (setq i (1+ i))
            )
            (vla-delete vla-path)
          )
        )
        (if temp-pl (entdel temp-pl))
        ;; 5. 복구 및 점프
        (setq *tsp-cip-dia* save-dia
              *tsp-cip-mode-idx* save-mode
              *tsp-cip-overlap* save-overlap
              *tsp-cip-equal-divide* save-equal-divide
              *tsp-cip-interval-idx* save-interval
              *tsp-cip-hpile-idx* save-hpile-idx
              *tsp-cip-grouting-idx* save-grouting)
        (setq seg-idx (1- j))
      )
    )
    (setq seg-idx (1+ seg-idx))
  )
  
  ;; 검증(Validation) 단계
  (setq total-counted-in-list 0 v-idx 0)
  (while (< v-idx (length *segment-list*))
    (if (= (cdr (assoc 'WALL-TYPE (nth v-idx *segment-list*))) "CIP")
      (setq total-counted-in-list (+ total-counted-in-list (nth v-idx *tsp-segment-pile-counts*)))
    )
    (setq v-idx (1+ v-idx))
  )
  
  (if (= total-counted-in-list *tsp-actual-drawn-hpiles*)
    (princ (strcat "\n[시스템 검증 성공] C.I.P 누적 캡슐 총합(" (itoa total-counted-in-list) ")과 실제 도면 생성 개수(" (itoa *tsp-actual-drawn-hpiles*) ")가 완벽히 일치합니다."))
    (princ (strcat "\n[시스템 검증 경고] C.I.P 개수 불일치 발생! 누적 총합: " (itoa total-counted-in-list) " / 실제 생성 개수: " (itoa *tsp-actual-drawn-hpiles*)))
  )
)


;;;;==========================================================================
;;;; defun tsp-find-next-dist-by-chord : 현재 점에서 목표 현의 길이(직선 거리)를 만족하는 곡선상의 다음 누적 거리를 이분법으로 탐색
;;;;==========================================================================
(defun tsp-find-next-dist-by-chord (curve-obj current-dist target-chord max-dist / 
                                    pt-current dist-low dist-high dist-mid 
                                    pt-mid current-chord tolerance iter max-iter pt-high)
  (setq pt-current (vlax-curve-getPointAtDist curve-obj current-dist))
  (setq dist-low current-dist)
  
  ;; 1차 검증: 남은 '경로 거리(Path)' 자체가 목표 간격보다 짧으면 탐색 불가 (폐합선 오류 방지)
  (if (< (- max-dist current-dist) target-chord)
    nil
    (progn
      ;; 상한선은 목표 직선거리의 1.5배 또는 전체 길이 중 작은 값으로 설정
      (setq dist-high (min (+ current-dist (* target-chord 1.5)) max-dist))
      
      ;; 상한선을 확장하는 안전장치 (곡률이 매우 심할 경우 대비)
      (while (and (< (distance pt-current (vlax-curve-getPointAtDist curve-obj dist-high)) target-chord)
                  (< dist-high max-dist))
        (setq dist-high (min (+ dist-high target-chord) max-dist))
      )
      
      (setq pt-high (vlax-curve-getPointAtDist curve-obj dist-high))
      
      ;; 최종 검증: max-dist까지 경로를 따라갔는데도 직선거리가 목표치보다 짧다면 도달 불가
      (if (and (= dist-high max-dist) (< (distance pt-current pt-high) target-chord))
        nil
        (progn
          (setq tolerance 0.01) ; 0.01mm 오차 허용
          (setq iter 0 max-iter 50)
          (setq dist-mid dist-low)
          
          ;; 이분법 정밀 탐색
          (while (and (< iter max-iter) (< tolerance (- dist-high dist-low)))
            (setq dist-mid (/ (+ dist-low dist-high) 2.0))
            (setq pt-mid (vlax-curve-getPointAtDist curve-obj dist-mid))
            (setq current-chord (distance pt-current pt-mid))
            
            (if (< current-chord target-chord)
              (setq dist-low dist-mid)
              (setq dist-high dist-mid)
            )
            (setq iter (1+ iter))
          )
          dist-mid
        )
      )
    )
  )
)



;;;;==========================================================================
;;;; defun tsp-make-segment-guideline : 세그먼트 구간 보조선 생성 (직접 좌표 계산으로 Offset 오류 원천 차단)
;;;;==========================================================================
(defun tsp-make-segment-guideline (pt1 pt2 dia boundary-orient / d seg-angle out-norm new-pt1 new-pt2 guide-ent)
  (setq d (/ dia 2.0))
  (setq seg-angle (angle pt1 pt2))
  (setq out-norm (+ seg-angle (* boundary-orient (/ pi 2.0))))
  
  ;; H-Pile(토류판)과 똑같이 바깥쪽을 향하도록 마이너스(-d) 방향으로 점 이동
  (setq new-pt1 (polar pt1 out-norm (- d)))
  (setq new-pt2 (polar pt2 out-norm (- d)))
  
  ;; 캐드 내장 OFFSET 명령어의 방향 플립(Flip) 버그에 의한 오검증 문제를 원천 차단하기 위해
  ;; 계산된 좌표로 보조 폴리선을 수학적으로 직접 강제 작도합니다.
  (entmake (list '(0 . "LWPOLYLINE") '(100 . "AcDbEntity") '(100 . "AcDbPolyline")
                 '(8 . "0") '(62 . 256) '(90 . 2) '(70 . 0)
                 (list 10 (car new-pt1) (cadr new-pt1))
                 (list 10 (car new-pt2) (cadr new-pt2))))
  (setq guide-ent (entlast))
  guide-ent
)
;;;; defun tsp-draw-cip-plan : C.I.P 평면도 작도 메인 제어 흐름


;;;;==========================================================================
;;;; defun tsp-draw-cip-plan : 전역 폴백용 CIP 작도를 세그먼트 엔진으로 통합
;;;;==========================================================================
(defun tsp-draw-cip-plan (boundary-ent boundary-orient / backup-segment-list backup-pile-counts backup-actual-hpiles backup-wall-type err)
  (setq backup-segment-list *segment-list*)
  (setq backup-pile-counts *tsp-segment-pile-counts*)
  (setq backup-actual-hpiles (if (boundp '*tsp-actual-drawn-hpiles*) *tsp-actual-drawn-hpiles* nil))
  (setq backup-wall-type *tsp-wall-type*)

  (setq err
    (vl-catch-all-apply
      '(lambda ()
         ;; 전역 폴백도 내부적으로는 세그먼트 기반으로 처리
         (init-segment-data boundary-ent boundary-orient nil)

         (if *segment-list*
           (progn
             (setq *tsp-wall-type* "CIP")
             (tsp-draw-cip-plan-per-segment boundary-ent boundary-orient)
           )
           (princ "\n[에러] 세그먼트 데이터 생성에 실패했습니다.")
         )
      )
      '()
    )
  )

  ;; 호출 전 상태 복원
  (setq *segment-list* backup-segment-list)
  (setq *tsp-segment-pile-counts* backup-pile-counts)
  (setq *tsp-actual-drawn-hpiles* backup-actual-hpiles)
  (setq *tsp-wall-type* backup-wall-type)

  (if (vl-catch-all-error-p err)
    (princ (strcat "\n[에러] 전역 CIP 폴백 통합 작도 중 오류: " (vl-catch-all-error-message err)))
  )

  (princ)
)


;;;;==========================================================================
;;;; defun draw-segment-numbers : 정렬된 vertices를 인자로 받아 세그먼트 번호 표기
;;;;==========================================================================
(defun draw-segment-numbers (boundary-ent boundary-orient vertices / is-closed num-verts max-segments seg-idx pt1 pt2 mid-pt seg-angle inward-angle text-pt text-h offset-dist layer-name circle-rad current-scale seg-data)
  (setq current-scale (if (and *tsp-scale-plan* (> *tsp-scale-plan* 0)) *tsp-scale-plan* 600.0))
  (princ (strcat "\n[INFO] 현재 적용 스케일: 1/" (rtos current-scale 2 0)))
  (setq text-h (* current-scale 2.5))
  (setq offset-dist (* current-scale 2.5))
  (setq circle-rad (* text-h 0.8))
  (setq layer-name "_번호")
  (create-layer-if-not-exists layer-name "2")
  (setq is-closed (is-closed-polyline boundary-ent))
  (setq num-verts (length vertices))
  (setq max-segments (if is-closed num-verts (- num-verts 1)))
  (setq seg-idx 0)
  (while (< seg-idx max-segments)
    (setq seg-data (nth seg-idx *segment-list*))
    
    ;; 세그먼트에 데이터 입력 여부(IS-DEFINED)와 상관없이 
    ;; 사용자가 경계선을 선택한 직후 무조건 번호표를 그려서 시각적으로 확인 가능하도록 조건문 해제
    (setq pt1 (nth seg-idx vertices))
    (setq pt2 (nth (if is-closed (rem (+ seg-idx 1) num-verts) (+ seg-idx 1)) vertices))
    (setq mid-pt (list (/ (+ (car pt1) (car pt2)) 2.0) (/ (+ (cadr pt1) (cadr pt2)) 2.0) 0.0))
    (setq seg-angle (angle pt1 pt2))
    (setq inward-angle (+ seg-angle (* boundary-orient (/ pi 2.0))))
    (setq text-pt (polar mid-pt inward-angle offset-dist))
    
    ;; 1. 텍스트 객체 생성 및 투명도 60 적용
    (entmake (list '(0 . "TEXT") (cons 8 layer-name) (cons 62 2)
                   (cons 10 text-pt) (cons 40 text-h)
                   (cons 1 (itoa (1+ seg-idx)))
                   '(72 . 4) (cons 11 text-pt)))
    (vla-put-EntityTransparency (vlax-ename->vla-object (entlast)) "60")
    
    ;; 2. 원(Circle) 객체 생성 및 투명도 60 적용
    (entmake (list '(0 . "CIRCLE") (cons 8 layer-name) (cons 62 2)
                   (cons 10 text-pt) (cons 40 circle-rad)))
    (vla-put-EntityTransparency (vlax-ename->vla-object (entlast)) "60")
    
    (setq seg-idx (1+ seg-idx))
  )
)


;;;;==========================================================================
;;;; defun draw-corner-numbers : 모서리 지시선 작도
;;;;==========================================================================
(defun draw-corner-numbers (boundary-ent boundary-orient vertices / is-closed num-verts i v-prev v-curr v-next p1-s p1-e p2-s p2-e n1 n2 offset-pt angle-dir line-start line1-end cap-center cap-top cap-bot line2-end circle-center text-h-num text-h-cnt layer-name text-val current-scale s-factor cap-w-half cap-h-half cap-rad angle-perp offset-dist line1-len line2-len circle-rad text-angle is-convex base-data final-data wedge-len wedge-half-ang cur-item prev-idx next-idx prev-item next-item ang-to-prev ang-to-next diff orig-dist cumulative-counts current-count p-seg-idx c-seg-idx p-def c-def is-active max-segments prev-active next-active is-open-end can-rotate seg-mid-count total-count cur-cum-count fully-closed active-flags mid-line-len cap1-bot cap1-center cap1-top cap2-bot cap2-center cap2-top draw-capsule-shape check-wedge-collision evade-angles orig-angle-dir test-idx evade-sign)


;;;;==========================================================================
;;;; defun draw-capsule-shape : 모서리 번호 캡슐 작도
;;;;==========================================================================
  (defun draw-capsule-shape (center-pt ang-dir ang-perp h-half w-half rad l-name col / p-c1 p-c2 p-c3 p-c4 p-c5 p-c6 p-c7 p-c8)
    (setq p-c1 (polar (polar center-pt ang-perp (- w-half rad)) ang-dir h-half))
    (setq p-c2 (polar (polar center-pt ang-perp w-half) ang-dir (- h-half rad)))
    (setq p-c3 (polar (polar center-pt ang-perp w-half) (+ ang-dir pi) (- h-half rad)))
    (setq p-c4 (polar (polar center-pt ang-perp (- w-half rad)) (+ ang-dir pi) h-half))
    (setq p-c5 (polar (polar center-pt (- ang-perp pi) (- w-half rad)) (+ ang-dir pi) h-half))
    (setq p-c6 (polar (polar center-pt (- ang-perp pi) w-half) (+ ang-dir pi) (- h-half rad)))
    (setq p-c7 (polar (polar center-pt (- ang-perp pi) w-half) ang-dir (- h-half rad)))
    (setq p-c8 (polar (polar center-pt (- ang-perp pi) (- w-half rad)) ang-dir h-half))
    (entmake (list '(0 . "LWPOLYLINE") '(100 . "AcDbEntity") '(100 . "AcDbPolyline")
                   (cons 8 l-name) (cons 62 col) '(90 . 8) '(70 . 1)
                   (cons 10 p-c1) '(42 . 0.41421356) (cons 10 p-c2) '(42 . 0.0)
                   (cons 10 p-c3) '(42 . 0.41421356) (cons 10 p-c4) '(42 . 0.0)
                   (cons 10 p-c5) '(42 . 0.41421356) (cons 10 p-c6) '(42 . 0.0)
                   (cons 10 p-c7) '(42 . 0.41421356) (cons 10 p-c8) '(42 . 0.0)))
  )


;;;;==========================================================================
;;;; defun check-wedge-collision : 모서리 번호표 간섭 검사 (한계치 3000으로 완화)
;;;;==========================================================================
  (defun check-wedge-collision (pt1 ang1 pt2 ang2 len half-ang s-factor / p1-L p1-R p2-L p2-R p1-C p2-C res C1 C2 dist-limit)
    (setq p1-L (polar pt1 (+ ang1 half-ang) len))
    (setq p1-R (polar pt1 (- ang1 half-ang) len))
    (setq p2-L (polar pt2 (+ ang2 half-ang) len))
    (setq p2-R (polar pt2 (- ang2 half-ang) len))
    (setq p1-C (polar pt1 ang1 len))
    (setq p2-C (polar pt2 ang2 len))
    (setq res nil)
    (if (inters pt1 p1-L pt2 p2-R) (setq res T))
    (if (inters pt1 p1-R pt2 p2-L) (setq res T))
    (if (inters pt1 p1-L pt2 p2-L) (setq res T))
    (if (inters pt1 p1-R pt2 p2-R) (setq res T))
    (if (inters pt1 p1-C pt2 p2-C) (setq res T))
    (setq C1 (polar pt1 ang1 (* 4000.0 s-factor)))
    (setq C2 (polar pt2 ang2 (* 4000.0 s-factor)))
    ;; 번호표 캡슐 간 거리를 기존 4500에서 3000으로 줄여 합리적인 45도 회피가 기각되지 않도록 조정
    (setq dist-limit (* 3000.0 s-factor))
    (if (< (distance C1 C2) dist-limit) (setq res T))
    res
  )

;;;;==========================================================================
;;;; defun check-boundary-collision : 지시선이 경계선과 교차하거나 완전히 겹치는지 검사
;;;;==========================================================================
  (defun check-boundary-collision (v-pt ang v-prev v-next / p-start p-end res ang-p ang-n diff-p diff-n)
    ;; 정점(Vertex)에서 10mm 띄워서 시작하여 원점 겹침 오류(False Positive) 방지
    (setq p-start (polar v-pt ang 10.0))
    (setq p-end (polar v-pt ang 5000.0))
    (setq res nil)
    
    ;; 1. 선분 교차 검사 (경계선 내부를 직접적으로 파고드는 경우)
    (if v-prev (if (inters p-start p-end v-pt v-prev T) (setq res T)))
    (if v-next (if (inters p-start p-end v-pt v-next T) (setq res T)))
    
    ;; 2. 평행 겹침 검사 (지시선이 경계선과 5도 이내로 나란하게 그려지는 경우 차단)
    (if (not res)
      (progn
        (if v-prev
          (progn
            (setq ang-p (angle v-pt v-prev))
            (setq diff-p (abs (- ang ang-p)))
            (while (> diff-p pi) (setq diff-p (abs (- diff-p (* 2.0 pi)))))
            (if (< diff-p (* 5.0 (/ pi 180.0))) (setq res T))
          )
        )
        (if v-next
          (progn
            (setq ang-n (angle v-pt v-next))
            (setq diff-n (abs (- ang ang-n)))
            (while (> diff-n pi) (setq diff-n (abs (- diff-n (* 2.0 pi)))))
            (if (< diff-n (* 5.0 (/ pi 180.0))) (setq res T))
          )
        )
      )
    )
    res
  )
  (setq current-scale (if (and *tsp-scale-plan* (> *tsp-scale-plan* 0)) *tsp-scale-plan* 600.0))
  (setq s-factor (/ current-scale 600.0))
  (setq layer-name "_지시")
  (create-layer-if-not-exists layer-name "2")
  (setq offset-dist (* 1000.0 s-factor))
  (setq line1-len (* 1300.0 s-factor))
  (setq cap-h-half (* 600.0 s-factor))
  (setq cap-w-half (* 1195.0 s-factor))
  (setq cap-rad (* 480.0 s-factor))
  (setq line2-len (* 1300.0 s-factor))
  (setq circle-rad (* 1200.0 s-factor))
  (setq text-h-num (* 840.0 s-factor))
  (setq text-h-cnt (* 720.0 s-factor))
  (setq wedge-len (* 7614.0 s-factor))
  (setq wedge-half-ang 0.245)
  (setq is-closed (is-closed-polyline boundary-ent))
  (setq num-verts (length vertices))
  (setq max-segments (if is-closed num-verts (- num-verts 1)))
  (setq fully-closed is-closed)
  (if is-closed
    (foreach seg *segment-list*
      (if (not (cdr (assoc 'IS-DEFINED seg))) (setq fully-closed nil))
    )
  )
  (setq cumulative-counts '())
  (setq current-count 0)
  (setq active-flags '())
  (setq i 0)
  (while (< i num-verts)
    (setq p-seg-idx (if (= i 0) (if is-closed (1- num-verts) -1) (1- i)))
    (setq c-seg-idx (if (>= i max-segments) -1 i))
      (setq p-def (if (>= p-seg-idx 0) (cdr (assoc 'IS-DEFINED (nth p-seg-idx *segment-list*))) nil))
      (setq c-def (if (>= c-seg-idx 0) (cdr (assoc 'IS-DEFINED (nth c-seg-idx *segment-list*))) nil))
      (setq is-active (or p-def c-def))
      (setq active-flags (append active-flags (list (cons i is-active))))
     (if is-active
        (progn
          (setq p-type (if (and (>= p-seg-idx 0) p-def) (cdr (assoc 'WALL-TYPE (nth p-seg-idx *segment-list*))) "NONE"))
          (setq c-type (if (and (>= c-seg-idx 0) c-def) (cdr (assoc 'WALL-TYPE (nth c-seg-idx *segment-list*))) "NONE"))
          ;; [추가] C.I.P 벽체의 시작점인지 판별 (i=0 이거나, 이전 세그먼트가 CIP가 아닌 경우)
          (setq is-cip-start (and (= c-type "CIP") (or (= i 0) (not (= p-type "CIP")))))

          ;; H-Pile이 포함된 코너이거나, C.I.P 벽체의 시작점일 경우 코너 카운트 +1
          (if (or (= p-type "HPILE") (= c-type "HPILE") is-cip-start)
            (setq current-count (1+ current-count))
          )
          
          (setq cumulative-counts (append cumulative-counts (list (cons i current-count))))
          
          (if c-def
            (progn
              (setq seg-mid-count (nth c-seg-idx *tsp-segment-pile-counts*))
              (if (null seg-mid-count) (setq seg-mid-count 0))
              
              ;; [추가] C.I.P 시작점에서 이미 +1을 했으므로, 중복 카운트를 막기 위해 구간 개수에서 1 차감
              (if (and is-cip-start (> seg-mid-count 0))
                (setq seg-mid-count (1- seg-mid-count))
              )
              
              (setq current-count (+ current-count seg-mid-count))
            )
          )
        )
      )
    (setq i (1+ i))
  )
  (setq total-count current-count)
  (setq base-data '())
  (setq i 0)
  (while (< i num-verts)
    (setq v-curr (nth i vertices))
    (if is-closed
      (progn (setq v-prev (nth (if (= i 0) (1- num-verts) (1- i)) vertices)) (setq v-next (nth (if (= i (1- num-verts)) 0 (1+ i)) vertices)))
      (progn (setq v-prev (if (= i 0) nil (nth (1- i) vertices))) (setq v-next (if (= i (1- num-verts)) nil (nth (1+ i) vertices))))
    )
    (setq is-convex nil)
    (if (and v-prev v-next) (setq is-convex (is-corner-convex v-prev v-curr v-next boundary-orient)))
    (setq is-open-end (not (and v-prev v-next)))
    (setq offset-pt nil)
    (if (and v-prev v-next)
      (progn
        (setq n1 (- (angle v-prev v-curr) (* boundary-orient (/ pi 2.0))))
        (setq n2 (- (angle v-curr v-next) (* boundary-orient (/ pi 2.0))))
        (setq p1-s (polar v-prev n1 offset-dist)) (setq p1-e (polar v-curr n1 offset-dist))
        (setq p2-s (polar v-curr n2 offset-dist)) (setq p2-e (polar v-next n2 offset-dist))
        (setq offset-pt (inters p1-s p1-e p2-s p2-e nil))
        (if (null offset-pt) (setq offset-pt (polar v-curr n1 offset-dist)))
      )
      (if v-next
        (progn (setq n2 (- (angle v-curr v-next) (* boundary-orient (/ pi 2.0)))) (setq offset-pt (polar v-curr n2 offset-dist)))
        (progn (setq n1 (- (angle v-prev v-curr) (* boundary-orient (/ pi 2.0)))) (setq offset-pt (polar v-curr n1 offset-dist)))
      )
    )
    (setq angle-dir (angle v-curr offset-pt))
    (setq is-active (cdr (assoc i active-flags)))
    (setq base-data (append base-data (list (list offset-pt angle-dir is-convex v-curr is-active is-open-end))))
    (setq i (1+ i))
  )
  (setq final-data '())
  (setq i 0)
  (while (< i num-verts)
    (setq cur-item (nth i base-data))
    (setq offset-pt (car cur-item)) (setq angle-dir (cadr cur-item))
    (setq is-convex (caddr cur-item)) (setq v-curr (cadddr cur-item))
    (setq is-active (nth 4 cur-item)) (setq is-open-end (nth 5 cur-item))
    (setq can-rotate (or is-convex is-open-end))
    (if (and is-active can-rotate)
      (progn
        (setq orig-dist (distance v-curr offset-pt))
        (setq prev-idx (if (= i 0) (1- num-verts) (1- i)))
        
        ;; 경계선 교차 검사를 위해 이전/다음 정점(Vertex) 추출
        (setq v-prev (if (= i 0) (if is-closed (nth (1- num-verts) vertices) nil) (nth (1- i) vertices)))
        (setq v-next (if (= i (1- num-verts)) (if is-closed (nth 0 vertices) nil) (nth (1+ i) vertices)))
        
        ;; 회피 각도 리스트 (45 -> 90 -> 30 -> 60 -> 15 -> 75)
        (setq evade-angles (list (/ pi 4.0) (/ pi 2.0) (/ pi 6.0) (/ pi 3.0) (/ pi 12.0) (* 5.0 (/ pi 12.0))))
        
        ;; 이전 모서리 검사
        (if (or is-closed (and (> i 0) (not is-closed)))
          (progn
            (setq prev-item (nth prev-idx base-data))
            (setq prev-active (nth 4 prev-item))
            (setq orig-angle-dir angle-dir)
            (setq test-idx 0)
            ;; 번호표끼리의 충돌(check-wedge-collision) 뿐만 아니라 경계선 교차(check-boundary-collision) 중 하나라도 걸리면 계속 회피각 탐색
            (while (and prev-active (< test-idx (length evade-angles)) 
                        (or (check-wedge-collision offset-pt angle-dir (car prev-item) (cadr prev-item) wedge-len wedge-half-ang s-factor)
                            (check-boundary-collision v-curr angle-dir v-prev v-next)))
              (setq ang-to-prev (angle offset-pt (car prev-item)))
              (setq diff (- ang-to-prev orig-angle-dir))
              (while (> diff pi) (setq diff (- diff (* 2.0 pi))))
              (while (< diff (- pi)) (setq diff (+ diff (* 2.0 pi))))
              (setq evade-sign (if (> diff 0) -1.0 1.0))
              (setq angle-dir (+ orig-angle-dir (* evade-sign (nth test-idx evade-angles))))
              (setq offset-pt (polar v-curr angle-dir orig-dist))
              (setq test-idx (1+ test-idx))
            )
          )
        )
        (setq next-idx (if (= i (1- num-verts)) 0 (1+ i)))
        (if (or is-closed (and (< i (1- num-verts)) (not is-closed)))
          (progn
            (setq next-item (nth next-idx base-data))
            (setq next-active (nth 4 next-item))
            (setq orig-angle-dir angle-dir)
            (setq test-idx 0)
            ;; 다음 모서리 번호표 충돌 검사에도 경계선 교차 검사 동시 적용
            (while (and next-active (< test-idx (length evade-angles)) 
                        (or (check-wedge-collision offset-pt angle-dir (car next-item) (cadr next-item) wedge-len wedge-half-ang s-factor)
                            (check-boundary-collision v-curr angle-dir v-prev v-next)))
              (setq ang-to-next (angle offset-pt (car next-item)))
              (setq diff (- ang-to-next orig-angle-dir))
              (while (> diff pi) (setq diff (- diff (* 2.0 pi))))
              (while (< diff (- pi)) (setq diff (+ diff (* 2.0 pi))))
              (setq evade-sign (if (> diff 0) -1.0 1.0))
              (setq angle-dir (+ orig-angle-dir (* evade-sign (nth test-idx evade-angles))))
              (setq offset-pt (polar v-curr angle-dir orig-dist))
              (setq test-idx (1+ test-idx))
            )
          )
        )
      )
    )
    (setq final-data (append final-data (list (list offset-pt angle-dir v-curr is-active))))
    (setq i (1+ i))
  )
  (setq i 0)
  (while (< i num-verts)
    (setq cur-item (nth i final-data))
    (setq line-start (car cur-item)) (setq angle-dir (cadr cur-item))
    (setq v-curr (caddr cur-item)) (setq is-active (nth 3 cur-item))
    (if is-active
      (progn
        (setq angle-perp (+ angle-dir (/ pi 2.0)))
        (setq text-angle (- angle-dir (/ pi 2.0)))
        (setq text-val (1+ i))
        (setq cur-cum-count (cdr (assoc i cumulative-counts)))
        (if (and fully-closed (= i 0))
          (progn
            (setq mid-line-len (* 600.0 s-factor))
            (setq cap1-bot (polar line-start angle-dir line1-len))
            (setq cap1-center (polar cap1-bot angle-dir cap-h-half))
            (setq cap1-top (polar cap1-center angle-dir cap-h-half))
            (setq cap2-bot (polar cap1-top angle-dir mid-line-len))
            (setq cap2-center (polar cap2-bot angle-dir cap-h-half))
            (setq cap2-top (polar cap2-center angle-dir cap-h-half))
            (setq line2-end (polar cap2-top angle-dir line2-len))
            (setq circle-center (polar line2-end angle-dir circle-rad))
            (entmake (list '(0 . "LINE") (cons 8 layer-name) (cons 62 1) (cons 10 line-start) (cons 11 cap1-bot)))
            (entmake (list '(0 . "LINE") (cons 8 layer-name) (cons 62 1) (cons 10 cap1-top) (cons 11 cap2-bot)))
            (entmake (list '(0 . "LINE") (cons 8 layer-name) (cons 62 2) (cons 10 cap2-top) (cons 11 line2-end)))
            (draw-capsule-shape cap1-center angle-dir angle-perp cap-h-half cap-w-half cap-rad layer-name 1)
            (draw-capsule-shape cap2-center angle-dir angle-perp cap-h-half cap-w-half cap-rad layer-name 1)
            (entmake (list '(0 . "CIRCLE") (cons 8 layer-name) (cons 62 2) (cons 10 circle-center) (cons 40 circle-rad)))
            (entmake (list '(0 . "TEXT") (cons 8 layer-name) (cons 62 7) (cons 10 cap1-center) (cons 40 text-h-cnt) (cons 50 text-angle) (cons 1 (itoa total-count)) '(72 . 4) (cons 11 cap1-center)))
            (entmake (list '(0 . "TEXT") (cons 8 layer-name) (cons 62 7) (cons 10 cap2-center) (cons 40 text-h-cnt) (cons 50 text-angle) (cons 1 (itoa cur-cum-count)) '(72 . 4) (cons 11 cap2-center)))
            (entmake (list '(0 . "TEXT") (cons 8 layer-name) (cons 62 7) (cons 10 circle-center) (cons 40 text-h-num) (cons 50 text-angle) (cons 1 (itoa text-val)) '(72 . 4) (cons 11 circle-center)))
          )
          (progn
            (setq cap-bot (polar line-start angle-dir line1-len))
            (setq cap-center (polar cap-bot angle-dir cap-h-half))
            (setq cap-top (polar cap-center angle-dir cap-h-half))
            (setq line2-end (polar cap-top angle-dir line2-len))
            (setq circle-center (polar line2-end angle-dir circle-rad))
            (entmake (list '(0 . "LINE") (cons 8 layer-name) (cons 62 1) (cons 10 line-start) (cons 11 cap-bot)))
            (entmake (list '(0 . "LINE") (cons 8 layer-name) (cons 62 2) (cons 10 cap-top) (cons 11 line2-end)))
            (draw-capsule-shape cap-center angle-dir angle-perp cap-h-half cap-w-half cap-rad layer-name 1)
            (entmake (list '(0 . "CIRCLE") (cons 8 layer-name) (cons 62 2) (cons 10 circle-center) (cons 40 circle-rad)))
            (entmake (list '(0 . "TEXT") (cons 8 layer-name) (cons 62 7) (cons 10 cap-center) (cons 40 text-h-cnt) (cons 50 text-angle) (cons 1 (itoa cur-cum-count)) '(72 . 4) (cons 11 cap-center)))
            (entmake (list '(0 . "TEXT") (cons 8 layer-name) (cons 62 7) (cons 10 circle-center) (cons 40 text-h-num) (cons 50 text-angle) (cons 1 (itoa text-val)) '(72 . 4) (cons 11 circle-center)))
          )
        )
      )
    )
    (setq i (1+ i))
  )
)


;;;;==========================================================================
;;;; defun tsp-calculate-brace-limit : 사보강재 한계거리(절대/권장) 산출
;;;;==========================================================================
(defun tsp-calculate-brace-limit (idx / is-closed num-segs prev-idx next-idx curr-seg prev-seg next-seg L1 L2 curr-brace prev-brace next-brace prev-used next-used margin1 margin2 avail1 avail2 hard-limit soft-limit curr-b prev-b next-b s-limit1 s-limit2)
  (setq num-segs (length *segment-list*))
  (setq curr-seg (nth idx *segment-list*))
  (setq L2 (/ (cdr (assoc 'LENGTH curr-seg)) 1000.0))
  ;; 현재 모서리(idx)의 사보강재 폭(B) 추출 (없으면 기본 300)
  (setq curr-brace (cdr (assoc 'CORNER-BRACE curr-seg)))
  (setq curr-b 300.0)
  (if (and curr-brace (= (car curr-brace) "Y") (cadr curr-brace))
    (setq curr-b (float (nth 1 (cadr (last (cadr curr-brace))))))
  )
  (if (and *tsp-boundary-ent* (is-closed-polyline *tsp-boundary-ent*))
    (setq is-closed T)
    (setq is-closed nil)
  )
  (setq prev-idx (if (= idx 0) (if is-closed (1- num-segs) -1) (1- idx)))
  (setq next-idx (if (= idx (1- num-segs)) (if is-closed 0 -1) (1+ idx)))
  ;; 1. 이전 선분(L1) 가용성 검사
  (if (>= prev-idx 0)
    (progn
      (setq prev-seg (nth prev-idx *segment-list*))
      (setq L1 (/ (cdr (assoc 'LENGTH prev-seg)) 1000.0))
      (setq prev-brace (cdr (assoc 'CORNER-BRACE prev-seg)))
      (setq prev-b 300.0 prev-used 0.0)
      (if (and prev-brace (= (car prev-brace) "Y"))
        (if (cadr prev-brace)
          (progn
            (setq prev-used (nth 2 (last (cadr prev-brace))))
            (setq prev-b (float (nth 1 (cadr (last (cadr prev-brace))))))
          )
          ;; 미입력 상태: 무조건 최소 1.0m만 예약 (유연한 배분)
          (setq prev-used 1.0)
        )
      )
      ;; [동적 마진 계산] (나의 B/2 + 이웃의 B/2) * 1.414(45도 빗변) + 화타쐐기 여유 150mm
      (setq margin1 (+ (* (+ (/ curr-b 2000.0) (/ prev-b 2000.0)) 1.414) 0.15))
      (setq avail1 (- L1 prev-used margin1))
    )
    (progn (setq L1 999.0) (setq avail1 999.0) (setq prev-brace nil))
  )
  ;; 2. 현재 선분(L2) 가용성 검사
  (if (>= next-idx 0)
    (progn
      (setq next-seg (nth next-idx *segment-list*))
      (setq next-brace (cdr (assoc 'CORNER-BRACE next-seg)))
      (setq next-b 300.0 next-used 0.0)
      (if (and next-brace (= (car next-brace) "Y"))
        (if (cadr next-brace)
          (progn
            (setq next-used (nth 2 (last (cadr next-brace))))
            (setq next-b (float (nth 1 (cadr (last (cadr next-brace))))))
          )
          ;; 미입력 상태: 최소 1.0m 예약
          (setq next-used 1.0)
        )
      )
      (setq margin2 (+ (* (+ (/ curr-b 2000.0) (/ next-b 2000.0)) 1.414) 0.15))
      (setq avail2 (- L2 next-used margin2))
    )
    (progn (setq L2 999.0) (setq avail2 999.0) (setq next-brace nil))
  )
  ;; 3. 최종 이중 한계치 도출 (List 형태로 반환)
  (setq hard-limit (min avail1 avail2))
  (if (< hard-limit 0.0) (setq hard-limit 0.0))
  ;; 이웃 모서리에 사보강재가 없을 경우 50% 제한을 해제하고 해당 방향의 물리적 한계치 적용
  (setq s-limit1 (if (and prev-brace (= (car prev-brace) "Y")) (/ L1 2.0) avail1))
  (setq s-limit2 (if (and next-brace (= (car next-brace) "Y")) (/ L2 2.0) avail2))
  (setq soft-limit (min s-limit1 s-limit2))
  ;; 만약 권장 한계(soft-limit)가 계산상 절대 한계(hard-limit)보다 커진다면 절대 한계로 하향 고정
  (if (> soft-limit hard-limit) (setq soft-limit hard-limit))
  (list hard-limit soft-limit)
)

;;;;==========================================================================
;;;; defun tsp-is-point-in-triangle : 한 점이 세 꼭짓점으로 이루어진 삼각형 내부에 있는지 판별
;;;;==========================================================================
(defun tsp-is-point-in-triangle (pt p1 p2 p3 / sign-func d1 d2 d3 has_neg has_pos)
  (defun sign-func (pt1 pt2 pt3)
    (- (* (- (car pt1) (car pt3)) (- (cadr pt2) (cadr pt3)))
       (* (- (car pt2) (car pt3)) (- (cadr pt1) (cadr pt3))))
  )
  (setq d1 (sign-func pt p1 p2))
  (setq d2 (sign-func pt p2 p3))
  (setq d3 (sign-func pt p3 p1))
  (setq has_neg (or (< d1 0.0) (< d2 0.0) (< d3 0.0)))
  (setq has_pos (or (> d1 0.0) (> d2 0.0) (> d3 0.0)))
  (not (and has_neg has_pos))
)

;;;;==========================================================================
;;;; defun tsp-delete-manual-post-by-segment : 중간말뚝 수동 추가/삭제/초기화
;;;;==========================================================================
(defun tsp-delete-manual-post-by-segment (target-id / new-list added-list del-list new-del-list post-record ins_pt ss i ent ent-data pt process-and-delete process-deleted-pts ss-struts valid-triangles j e-data xdata x-vals t-p1 t-p2 t-p3 tri)
  (setq new-list '() new-del-list '())
  
  ;; 1. 현재 타겟 세그먼트(target-id)에 속한 사보강재(TRI) 및 버팀보(RECT) 영역 데이터 수집
  (setq valid-triangles '())
  ;; [버그수정] 사보강재만 검색하던 것을 사보강재+버팀보 모두 검색하도록 수정
  (setq ss-struts (ssget "X" '((0 . "LWPOLYLINE") (8 . "_사보강재(Corner_Strut),_버팀보(Strut)"))))
  (if ss-struts
    (progn
      (setq j 0)
      (while (< j (sslength ss-struts))
        (setq e-data (entget (ssname ss-struts j) '("TSP_STRUT_SPEC")))
        (setq cur-layer (cdr (assoc 8 e-data)))
        (setq xdata (assoc -3 e-data))
        (if xdata
          (progn
            (setq x-vals (cdr (car (cdr xdata))))
            ;; [버그수정] (= length 8)을 (>= length 8)로 변경하여 버팀보(길이 10)도 포함
            (if (>= (length x-vals) 8)
              (progn
                (if (= (cdr (nth 0 x-vals)) target-id)
                  (progn
                    (if (= cur-layer "_사보강재(Corner_Strut)")
                      (progn
                        ;; 사보강재: TRI 영역 수집
                        (setq t-p1 (cdr (nth 5 x-vals)))
                        (setq t-p2 (cdr (nth 6 x-vals)))
                        (setq t-p3 (cdr (nth 7 x-vals)))
                        (setq valid-triangles (append valid-triangles (list (list "TRI" t-p1 t-p2 t-p3))))
                      )
                      (progn
                        ;; 버팀보: RECT 영역 수집
                        (setq s-p1 (cdr (nth 2 x-vals)))
                        (setq s-p2 (cdr (nth 3 x-vals)))
                        (setq s-width (cdr (nth 1 x-vals)))
                        (setq valid-triangles (append valid-triangles (list (list "RECT" s-p1 s-p2 s-width))))
                      )
                    )
                  )
                )
              )
            )
          )
        )
        (setq j (1+ j))
      )
    )
  )

  ;; 2. 도면에 그려진 모든 중간말뚝 블록을 화면에서 스캔하여 대기 (물리적 삭제용)
  (setq ss (ssget "X" '((0 . "INSERT") (8 . "_중간말뚝(Post pile)"))))
  
  ;; 3. 내부 함수: 수동 추가(ADDED_POSTS) 대상 판별 및 화면 객체 동기화 삭제
  (defun process-and-delete (record target / should-del s-ang d-proj d-perp)
    (setq ins_pt (nth 0 record))
    (setq should-del nil)
    
    ;; 판별 로직: 신버전(길이 8)은 ID로, 구버전(길이 7)은 수집된 TRI/RECT 공간 내부 여부로 판별
    (if (>= (length record) 8)
      (if (= (nth 7 record) target) (setq should-del T))
      (progn
        ;; [버그수정] TRI(사보강재)와 RECT(버팀보) 모두 지원
        (foreach zone valid-triangles
          (if (= (car zone) "TRI")
            (if (tsp-is-point-in-triangle ins_pt (nth 1 zone) (nth 2 zone) (nth 3 zone))
              (setq should-del T)
            )
            (progn
              ;; RECT 영역 판별
              (setq s-ang (angle (nth 1 zone) (nth 2 zone)))
              (setq d-proj (tsp-project-dist (nth 1 zone) s-ang ins_pt))
              (setq d-perp (abs (- (* (- (car ins_pt) (car (nth 1 zone))) (sin s-ang))
                                   (* (- (cadr ins_pt) (cadr (nth 1 zone))) (cos s-ang)))))
              (if (and (>= d-proj -10.0)
                       (<= d-proj (+ (distance (nth 1 zone) (nth 2 zone)) 10.0))
                       (<= d-perp (+ (nth 3 zone) 100.0)))
                (setq should-del T)
              )
            )
          )
        )
      )
    )

    (if should-del
      (progn
        (if ss
          (progn
            (setq i 0)
            (while (< i (sslength ss))
              (setq ent (ssname ss i))
              (if (entget ent)
                (progn
                  (setq ent-data (entget ent))
                  (setq pt (cdr (assoc 10 ent-data)))
                  (if (< (distance (list (car pt) (cadr pt) 0.0) (list (car ins_pt) (cadr ins_pt) 0.0)) 1.0)
                    (entdel ent)
                  )
                )
              )
              (setq i (1+ i))
            )
          )
        )
        nil ;; 리스트에서 제거 (완전 삭제)
      )
      T ;; 삭제 대상이 아니므로 보존
    )
  )

  ;; 3-1. 내부 함수: 수동 삭제(DELETED_POSTS) 판별용 (삭제 기록을 없애서 말뚝을 복원)
  (defun process-deleted-pts (pt-record / should-restore s-ang d-proj d-perp)
    (setq should-restore nil)
    ;; [버그수정] TRI(사보강재)와 RECT(버팀보) 모두 지원
    (foreach zone valid-triangles
      (if (= (car zone) "TRI")
        (if (tsp-is-point-in-triangle pt-record (nth 1 zone) (nth 2 zone) (nth 3 zone))
          (setq should-restore T)
        )
        (progn
          ;; RECT 영역 판별
          (setq s-ang (angle (nth 1 zone) (nth 2 zone)))
          (setq d-proj (tsp-project-dist (nth 1 zone) s-ang pt-record))
          (setq d-perp (abs (- (* (- (car pt-record) (car (nth 1 zone))) (sin s-ang))
                               (* (- (cadr pt-record) (cadr (nth 1 zone))) (cos s-ang)))))
          (if (and (>= d-proj -10.0)
                   (<= d-proj (+ (distance (nth 1 zone) (nth 2 zone)) 10.0))
                   (<= d-perp (+ (nth 3 zone) 100.0)))
            (setq should-restore T)
          )
        )
      )
    )
    (if should-restore nil T) ;; 복원 대상이면 기록 리스트에서 제거(nil), 아니면 유지(T)
  )

  ;; 4. 임시 메모리 또는 도면 영구 LDATA 데이터베이스 정리
  (if *tsp-use-temp-posts*
    (progn
      ;; [1] 수동 추가된 말뚝 정리
      (if *tsp-temp-added-posts*
        (progn
          (foreach post-record *tsp-temp-added-posts*
            (if (process-and-delete post-record target-id)
              (setq new-list (append new-list (list post-record)))
            )
          )
          (setq *tsp-temp-added-posts* new-list)
        )
      )
      ;; [2] 수동 삭제된 말뚝 복원 정리
      (if *tsp-temp-deleted-posts*
        (progn
          (foreach pt-record *tsp-temp-deleted-posts*
            (if (process-deleted-pts pt-record)
              (setq new-del-list (append new-del-list (list pt-record)))
            )
          )
          (setq *tsp-temp-deleted-posts* new-del-list)
        )
      )
    )
    (progn
      ;; [1] 수동 추가된 말뚝 정리
      (setq added-list (vlax-ldata-get "TSP_DICT" "ADDED_POSTS"))
      (if added-list
        (progn
          (foreach post-record added-list
            (if (process-and-delete post-record target-id)
              (setq new-list (append new-list (list post-record)))
            )
          )
          (vlax-ldata-put "TSP_DICT" "ADDED_POSTS" new-list)
        )
      )
      ;; [2] 수동 삭제된 말뚝 복원 정리
      (setq del-list (vlax-ldata-get "TSP_DICT" "DELETED_POSTS"))
      (if del-list
        (progn
          (foreach pt-record del-list
            (if (process-deleted-pts pt-record)
              (setq new-del-list (append new-del-list (list pt-record)))
            )
          )
          (vlax-ldata-put "TSP_DICT" "DELETED_POSTS" new-del-list)
        )
      )
    )
  )
  (setq *tsp-data-dirty* T)
)


;;; ==========================================================================
;;; [SECTION 6] DCL UI 및 콜백 (Dialog Interface)
;;; ==========================================================================

;;;;==========================================================================
;;;; defun tsp-get-exact-ry : H형강의 제원(H, B, tw, tf)을 적분하여 약축 단면 2차 반경(ry) 정밀 계산
;;;;==========================================================================
(defun tsp-get-exact-ry (h b tw tf / hw Iyw Iyf Iy Area ry)
  (setq hw (- h (* 2.0 tf)))
  (setq Iyw (/ (* hw (expt tw 3.0)) 12.0))
  (setq Iyf (/ (* tf (expt b 3.0)) 6.0))
  (setq Iy (+ Iyw Iyf))
  (setq Area (+ (* 2.0 b tf) (* hw tw)))
  (setq ry (sqrt (/ Iy Area)))
  ry
)

;;;;==========================================================================
;;;; defun tsp-calc-unsupported-length : 세장비 한계와 단면 제원을 바탕으로 허용 비지지길이(m) 산출
;;;;==========================================================================
(defun tsp-calc-unsupported-length (custom-vals slenderness-limit / h b tw tf ry max-len-mm)
  (if (and custom-vals (= (length custom-vals) 4))
    (progn
      (setq h (float (nth 0 custom-vals)))
      (setq b (float (nth 1 custom-vals)))
      (setq tw (float (nth 2 custom-vals)))
      (setq tf (float (nth 3 custom-vals)))
      (setq ry (tsp-get-exact-ry h b tw tf))
    )
    (setq ry (* 0.25 300.0)) ; 파싱 실패 시 기본값 H-300 약산 적용
  )
  (setq max-len-mm (* slenderness-limit ry))
  (/ max-len-mm 1000.0) ; m 단위 반환
)

;;;;==========================================================================
;;;; defun tsp-project-dist : 특정 각도(dir) 축에 대한 목표점의 투영 거리 산출 (스칼라 내적)
;;;;==========================================================================
(defun tsp-project-dist (base-pt dir-angle target-pt / vec target-vec dot)
  (setq vec (list (cos dir-angle) (sin dir-angle)))
  (setq target-vec (list (- (car target-pt) (car base-pt)) (- (cadr target-pt) (cadr base-pt))))
  (setq dot (+ (* (car vec) (car target-vec)) (* (cadr vec) (cadr target-vec))))
  dot
)


;;;;==========================================================================
;;;; defun create-tsp-dcl : 임시 DCL 파일을 생성하여 각종 UI 다이얼로그의 형태를 정의하고, 해당 파일의 경로를 반환하는 함수
;;;;==========================================================================
(defun create-tsp-dcl (/ dcl-file dcl-path)
  (setq dcl-path (strcat (getvar "TEMPPREFIX") "tsp.dcl"))
  (setq dcl-file (open dcl-path "w"))
  (if dcl-file
    (progn
     ;; ----------------------------------------------------------------------
      ;; [DCL 0] tsp_main_menu : 초기 시작 메뉴 (프로젝트 실행, 내보내기, 불러오기)
      ;; ----------------------------------------------------------------------
      (write-line "tsp_main_menu : dialog { label = \"TSP 메인 메뉴\"; " dcl-file)
      (write-line "  : column { alignment = centered; " dcl-file)
      (write-line "    : button { key = \"btn_run\"; label = \"프로젝트 실행 (도면작업)\"; width = 35; } " dcl-file)
      (write-line "    : spacer { height = 0.5; } " dcl-file)
      (write-line "    : button { key = \"btn_load_dwg\"; label = \"도면 내 프로젝트 불러오기\"; width = 35; } " dcl-file)
      (write-line "    : button { key = \"btn_export\"; label = \"EXCEL(CSV)로 내보내기\"; width = 35; } " dcl-file)
      (write-line "    : button { key = \"btn_import\"; label = \"EXCEL(CSV)에서 불러오기\"; width = 35; } " dcl-file)
      (write-line "    : spacer { height = 1.0; } " dcl-file)
      (write-line "    : button { key = \"cancel\"; label = \"종료\"; is_cancel = true; width = 35; } " dcl-file)
      (write-line "  } " dcl-file)
      (write-line "} " dcl-file)
      
      ;; ----------------------------------------------------------------------
      ;; [DCL 1] tsp_scale : 도면 스케일 설정
      ;; ----------------------------------------------------------------------
      (write-line "tsp_scale : dialog { label = \"스케일 설정\"; " dcl-file)
      (write-line "  : column { alignment = centered; " dcl-file)
      (write-line "    : row { alignment = centered; fixed_width = true; " dcl-file)
      (write-line "      : edit_box { key = \"scale_section\"; label = \"단면도 A3 : 1/\"; edit_width = 3; width = 10; fixed_width = true; } " dcl-file)
      (write-line "    } " dcl-file)
      (write-line "    : row { alignment = centered; fixed_width = true; " dcl-file)
      (write-line "      : edit_box { key = \"scale_plan\"; label = \"평면도 A3 : 1/\"; edit_width = 3; width = 10; fixed_width = true; } " dcl-file)
      (write-line "    } " dcl-file)
      (write-line "    } " dcl-file)
      (write-line "  : spacer { height = 1.0; } " dcl-file)
      (write-line "  : row { alignment = centered; : button { key = \"accept\"; label = \"확인\"; is_default = true; width = 12; } : button { key = \"back\"; label = \"이전\"; width = 12; } : button { key = \"cancel\"; label = \"취소\"; is_cancel = true; width = 12; } } }" dcl-file)
      
      ;; ----------------------------------------------------------------------
      ;; [DCL 2] tsp_load_list : 저장된 프로젝트 관리 및 불러오기
      ;; ----------------------------------------------------------------------
      (write-line "tsp_load_list : dialog { label = \"프로젝트 관리\"; " dcl-file)
      (write-line "  : list_box { key = \"proj_list\"; label = \"저장된 프로젝트:\"; width = 30; height = 10; } " dcl-file)
      (write-line "  : row { alignment = centered; : button { key = \"accept\"; label = \"불러오기\"; is_default = true; } : button { key = \"btn_del_proj\"; label = \"삭제\"; } : button { key = \"cancel\"; label = \"취소\"; is_cancel = true; } } }" dcl-file)
      
      ;; ----------------------------------------------------------------------
      ;; [DCL 3] tsp_save_prompt : 다른 이름으로 프로젝트 저장 확인
      ;; ----------------------------------------------------------------------
      (write-line "tsp_save_prompt : dialog { label = \"프로젝트 저장\"; " dcl-file)
      (write-line "  : text { label = \"다른 이름으로 저장하시겠습니까?\"; alignment = centered; } : spacer { height = 0.5; } " dcl-file)
      (write-line "  : row { alignment = centered; : button { key = \"btn_yes\"; label = \"예 (새로 저장)\"; is_default = true; width = 18; } : button { key = \"btn_no\"; label = \"아니오 (덮어쓰기)\"; width = 18; } : button { key = \"cancel\"; label = \"취소\"; is_cancel = true; width = 12; } } }" dcl-file)
      
      ;; ----------------------------------------------------------------------
      ;; [DCL 4] tsp_section_choice : 단면도 생성 유형 선택 (일반/모서리)
      ;; ----------------------------------------------------------------------
      (write-line "tsp_section_choice : dialog { label = \"단면도 생성 선택\"; : column { : text { label = \"작성할 단면도를 선택하세요:\"; alignment = centered; } : spacer { height = 0.5; } : toggle { key = \"chk_seg_sec\"; label = \"세그먼트(일반) 단면도\"; value = \"0\"; } : toggle { key = \"chk_cor_sec\"; label = \"모서리 사보강재(Corner Strut) 단면도\"; value = \"0\"; } : spacer { height = 0.5; } : row { alignment = centered; : button { key = \"accept\"; label = \"확인\"; is_default = true; width = 12; } : button { key = \"cancel\"; label = \"취소\"; is_cancel = true; width = 12; } } } }" dcl-file)
      
      ;; ----------------------------------------------------------------------
      ;; [DCL 5] tsp_manager : 세그먼트 메인 관리창
      ;; ----------------------------------------------------------------------
      (write-line "tsp_manager : dialog { key = \"manager_title\"; label = \"세그먼트 설정 (Segment Manager)\"; : column { " dcl-file)
      (write-line "  : row { " dcl-file)
      (write-line "    : text { label = \"No.\"; width = 4; } " dcl-file)
      (write-line "    : text { label = \"이름\"; width = 10; } " dcl-file)
      (write-line "    : text { label = \"단면\"; width = 6; } " dcl-file)
      (write-line "    : text { label = \"흙막이벽\"; width = 12; } " dcl-file)
      (write-line "    : text { label = \"H-pile/띠장 규격\"; width = 28; } " dcl-file)
      (write-line "    : text { label = \"지보재\"; width = 15; } " dcl-file)
      (write-line "    : text { label = \"사보강재(Corner Strut)\"; width = 25; } " dcl-file)
      (write-line "  }" dcl-file)
      ;; multiple_select = true; Shift 및 Ctrl 다중 선택
      (write-line "  : list_box { key = \"seg_list\"; width = 115; height = 15; fixed_width = true; fixed_height = true; allow_accept = true; multiple_select = true; tabs = \"5 15 21 33 60 75\"; } " dcl-file)
      (write-line "  : text { key = \"status_msg\"; value = \"목록을 선택하고 입력 버튼을 누르세요.\"; alignment = centered; } } : spacer { height = 0.2; } " dcl-file)
      (write-line "  : row { alignment = centered; : edit_box { key = \"project_name\"; label = \"프로젝트 이름:\"; width = 25; } : button { key = \"btn_load_proj\"; label = \"불러오기\"; width = 12; } : button { key = \"btn_save_proj\"; label = \"저장\"; width = 12; } } : spacer { height = 0.2; } " dcl-file)
      (write-line "  : row { alignment = centered; : button { key = \"btn_input\"; label = \"입력 (Input)\"; is_default = true; width = 18; } : button { key = \"btn_modify\"; label = \"수정 (Edit)\"; width = 18; } : button { key = \"btn_delete\"; label = \"초기화 (Reset)\"; width = 18; } : button { key = \"btn_copy_from\"; label = \"설정 가져오기\"; width = 22; } } " dcl-file)
      (write-line "  : row { alignment = centered; : button { key = \"btn_apply_all\"; label = \"전체 설정 일괄 적용\"; width = 30; } : button { key = \"btn_delete_all\"; label = \"전체 목록 초기화 (Reset All)\"; width = 30; } } " dcl-file)
      (write-line "  : row { alignment = centered; : button { key = \"btn_apply_soil\"; label = \"지반 정보 일괄 적용\"; width = 30; } : button { key = \"btn_apply_support\"; label = \"지보재 정보 일괄 적용\"; width = 30; } } " dcl-file)
      (write-line "  : row { alignment = centered; : button { key = \"btn_apply_wall\"; label = \"흙막이벽 정보 일괄 적용\"; width = 30; } : button { key = \"btn_apply_brace\"; label = \"사보강재 정보 일괄 적용\"; width = 30; } } : spacer { height = 0.5; } " dcl-file)
      (write-line "  : row { alignment = centered; : button { key = \"btn_measure\"; label = \"도면에서 확인/측정 (Measure)\"; width = 30; } } : spacer { height = 1.0; } " dcl-file)
      (write-line "  : row { alignment = centered; : button { key = \"btn_draw_section\"; label = \"단면도 생성 (Section)\"; width = 25; } : button { key = \"btn_draw_plan\"; label = \"평면도 생성 (Plan)\"; width = 25; } : button { key = \"cancel\"; label = \"종료 (Exit)\"; is_cancel = true; width = 20; } } }" dcl-file)
      
      ;; ----------------------------------------------------------------------
      ;; [DCL 6] tsp_edit_menu : 개별 세그먼트 상세 설정 (지반/흙막이/지보재 등)
      ;; ----------------------------------------------------------------------
      (write-line "tsp_edit_menu : dialog { key = \"menu_title\"; label = \"세그먼트 설정 수정\"; " dcl-file)
      (write-line "  : column { " dcl-file)
      (write-line "    : row { : edit_box { key = \"seg_name\"; label = \"이름 입력 :\"; width = 20; } : toggle { key = \"chk_section\"; label = \"단면생성 (지반 정보 포함)\"; } } " dcl-file)
      (write-line "    : spacer { height = 0.5; } " dcl-file)
      (write-line "    : button { key = \"btn_soil\"; label = \"지반 정의 (Soil)\"; width = 40; fixed_width = true; alignment = centered; } " dcl-file)
      (write-line "    : button { key = \"btn_wall\"; label = \"흙막이벽 정의 (Wall)\"; width = 40; fixed_width = true; alignment = centered; } " dcl-file)
      (write-line "    : button { key = \"btn_support\"; label = \"지보재 정의 (Support)\"; width = 40; fixed_width = true; alignment = centered; } " dcl-file)
      (write-line "    : button { key = \"btn_brace\"; label = \"사보강재(Corner Strut) 정의\"; width = 40; fixed_width = true; alignment = centered; } " dcl-file)
      (write-line "  } " dcl-file)
      (write-line "  : spacer { height = 1; } " dcl-file)
      (write-line "  : row { alignment = centered; : button { key = \"accept\"; label = \"확인 (저장)\"; is_default = true; width = 15; } : button { key = \"cancel\"; label = \"취소\"; is_cancel = true; width = 15; } } }" dcl-file)
      
      ;; ----------------------------------------------------------------------
      ;; [DCL 7] tsp_brace & tsp_brace_single : 사보강재(Corner Strut) 설정 다이얼로그
      ;; ----------------------------------------------------------------------
      (write-line "tsp_brace : dialog { key = \"brace_dlg_title\"; label = \"사보강재(Corner Strut) 설정\"; : column { " dcl-file)
      (write-line "  : text { key = \"brace_info\"; label = \"최대 한계 거리: -- m\"; alignment = centered; } " dcl-file)
      (write-line "  : list_box { key = \"brace_list\"; height = 6; width = 70; multiple_select = true; } " dcl-file)
      (write-line "  : row { " dcl-file)
      (write-line "    : text { label = \"이격 거리(m):\"; width = 12; } " dcl-file)
      (write-line "    : edit_box { key = \"brace_dist\"; width = 10; } " dcl-file)
      (write-line "  } " dcl-file)
      (write-line "  : text { label = \"※ 1열은 코너 기준, 2열부터는 이전 열 기준 상대거리입니다.\"; } " dcl-file)
      (write-line "  : spacer { height = 0.5; } " dcl-file)
      (write-line "  : text { label = \"사보강재(Corner Strut) 규격\"; } : popup_list { key = \"brace_spec\"; width = 30; } " dcl-file)
      (write-line "  : row { : edit_box { key = \"brace_h\"; width = 5; is_enabled = false; } : text { label = \"x\"; } : edit_box { key = \"brace_b\"; width = 5; is_enabled = false; } : text { label = \"x\"; } : edit_box { key = \"brace_tw\"; width = 5; is_enabled = false; } : text { label = \"/\"; } : edit_box { key = \"brace_tf\"; width = 5; is_enabled = false; } } " dcl-file)
      (write-line "  : spacer { height = 0.5; } " dcl-file)
      (write-line "  : row { : popup_list { key = \"brace_jack\"; label = \"잭 종류:\"; width = 20; } : popup_list { key = \"brace_conn\"; label = \"연결 방식:\"; width = 20; } } " dcl-file)
      (write-line "  : spacer { height = 0.5; } " dcl-file)
      (write-line "  : row { alignment = centered; : button { key = \"btn_add\"; label = \"추가\"; } : button { key = \"btn_mod\"; label = \"수정\"; } : button { key = \"btn_del\"; label = \"삭제\"; } } " dcl-file)
      (write-line "  : spacer { height = 0.5; } " dcl-file)
      (write-line "  : boxed_column { label = \"보강재(Brace) 설정\"; " dcl-file)
      (write-line "    : toggle { key = \"chk_stiffener_enable\"; label = \"보강재(Brace) 생성 적용\"; } " dcl-file)
      (write-line "    : row { : text { label = \"설계 세장비 한계:\"; width = 16; } : popup_list { key = \"slenderness_limit\"; width = 20; } } " dcl-file)
      (write-line "    : row { : toggle { key = \"chk_manual_interval\"; label = \"간격 입력(m):\"; width = 16; } : edit_box { key = \"stiffener_interval\"; width = 10; } } " dcl-file)
      (write-line "    : text { key = \"stiffener_info\"; label = \"계산된 필요 간격: -- m\"; alignment = centered; } " dcl-file)
      (write-line "    : row { : text { label = \"보강재 여유장(mm) :\"; width = 16; } : edit_box { key = \"stiffener_margin\"; width = 10; } } " dcl-file)
      (write-line "  } " dcl-file)
      (write-line "  : boxed_column { label = \"중간말뚝(Post pile) 설정\"; " dcl-file)
      (write-line "    : row { " dcl-file)
      (write-line "      : toggle { key = \"chk_post_enable\"; label = \"생성 적용\"; value = \"1\"; width = 12; } " dcl-file)
      (write-line "      : popup_list { key = \"post_layout_mode\"; label = \"배치:\"; width = 16; } " dcl-file)
      (write-line "      : toggle { key = \"chk_post_invert\"; label = \"교차 반전\"; } " dcl-file)
      (write-line "    } " dcl-file)
      (write-line "    : row { " dcl-file)
      (write-line "      : radio_row { key = \"post_side_grp\"; " dcl-file)
      (write-line "        : radio_button { key = \"post_side_L\"; label = \"보강재 왼쪽\"; value = \"1\"; } " dcl-file)
      (write-line "        : radio_button { key = \"post_side_R\"; label = \"보강재 오른쪽\"; } " dcl-file)
      (write-line "      } " dcl-file)
      (write-line "    } " dcl-file)
      (write-line "    : row { alignment = right; : button { key = \"btn_post_add\"; label = \"추가\"; width = 10; } : button { key = \"btn_post_del\"; label = \"삭제\"; width = 10; } : button { key = \"btn_post_reset\"; label = \"초기화\"; width = 10; } } " dcl-file)
      (write-line "  } " dcl-file)
      (write-line "  : boxed_row { label = \"코너부 띠장 상향 (Splice)\"; " dcl-file)
      (write-line "    : toggle { key = \"chk_upgrade_wale\"; label = \"사보강재(Corner Strut) 구간 띠장 상향 적용\"; is_enabled = false; } " dcl-file)
      (write-line "    : popup_list { key = \"upgrade_wale_spec\"; width = 20; is_enabled = false; } " dcl-file)
      (write-line "  } " dcl-file)
      (write-line "  : spacer { height = 0.5; } " dcl-file)
      (write-line "  : row { alignment = centered; : button { key = \"btn_measure\"; label = \"도면에서 확인/측정\"; width = 25; } } " dcl-file)
      (write-line "  : spacer { height = 0.5; } " dcl-file)
      (write-line "  : row { alignment = centered; : button { key = \"accept\"; label = \"다음\"; is_default = true; width = 12; } : button { key = \"btn_comp\"; label = \"완료\"; width = 12; } : button { key = \"cancel\"; label = \"취소\"; is_cancel = true; width = 12; } } } }" dcl-file)
      
      (write-line "tsp_brace_single : dialog {" dcl-file)
      (write-line "  key = \"brace_dlg_title\";" dcl-file)
      (write-line "  label = \"사보강재(Corner Strut) 설정\";" dcl-file)
      (write-line "  : column {" dcl-file)
      (write-line "    : text { key = \"brace_info\"; label = \"최대 한계 거리: -- m\"; alignment = centered; }" dcl-file)
      (write-line "    : list_box { key = \"brace_list\"; height = 6; width = 70; multiple_select = true; }" dcl-file)
      (write-line "    : row {" dcl-file)
      (write-line "      : text { label = \"이격 거리(m):\"; width = 12; }" dcl-file)
      (write-line "      : edit_box { key = \"brace_dist\"; width = 10; }" dcl-file)
      (write-line "    }" dcl-file)
      (write-line "    : text { label = \"※ 1열은 코너 기준, 2열부터는 이전 열 기준 상대거리입니다.\"; }" dcl-file)
      (write-line "    : spacer { height = 0.5; }" dcl-file)
      (write-line "    : text { label = \"사보강재(Corner Strut) 규격\"; }" dcl-file)
      (write-line "    : popup_list { key = \"brace_spec\"; width = 30; }" dcl-file)
      (write-line "    : row {" dcl-file)
      (write-line "      : edit_box { key = \"brace_h\"; width = 5; is_enabled = false; }" dcl-file)
      (write-line "      : text { label = \"x\"; }" dcl-file)
      (write-line "      : edit_box { key = \"brace_b\"; width = 5; is_enabled = false; }" dcl-file)
      (write-line "      : text { label = \"x\"; }" dcl-file)
      (write-line "      : edit_box { key = \"brace_tw\"; width = 5; is_enabled = false; }" dcl-file)
      (write-line "      : text { label = \"/\"; }" dcl-file)
      (write-line "      : edit_box { key = \"brace_tf\"; width = 5; is_enabled = false; }" dcl-file)
      (write-line "    }" dcl-file)
      (write-line "    : spacer { height = 0.5; }" dcl-file)
      (write-line "    : row {" dcl-file)
      (write-line "      : popup_list { key = \"brace_jack\"; label = \"잭 종류:\"; width = 20; }" dcl-file)
      (write-line "      : popup_list { key = \"brace_conn\"; label = \"연결 방식:\"; width = 20; }" dcl-file)
      (write-line "    }" dcl-file)
      (write-line "    : spacer { height = 0.5; }" dcl-file)
      (write-line "    : row {" dcl-file)
      (write-line "      alignment = centered;" dcl-file)
      (write-line "      : button { key = \"btn_add\"; label = \"추가\"; }" dcl-file)
      (write-line "      : button { key = \"btn_mod\"; label = \"수정\"; }" dcl-file)
      (write-line "      : button { key = \"btn_del\"; label = \"삭제\"; }" dcl-file)
      (write-line "    }" dcl-file)
      (write-line "    : spacer { height = 0.5; }" dcl-file)
      (write-line "    : boxed_column { label = \"보강재(Brace) 설정\"; " dcl-file)
      (write-line "      : toggle { key = \"chk_stiffener_enable\"; label = \"보강재(Brace) 생성 적용\"; } " dcl-file)
      (write-line "      : row { : text { label = \"설계 세장비 한계:\"; width = 16; } : popup_list { key = \"slenderness_limit\"; width = 20; } } " dcl-file)
      (write-line "      : row { : toggle { key = \"chk_manual_interval\"; label = \"보강재 간격 입력(m):\"; width = 16; } : edit_box { key = \"stiffener_interval\"; width = 10; } } " dcl-file)
      (write-line "      : text { key = \"stiffener_info\"; label = \"계산된 필요 간격: -- m\"; alignment = centered; } " dcl-file)
      (write-line "      : row { : text { label = \"보강재 여유장(mm) :\"; width = 16; } : edit_box { key = \"stiffener_margin\"; width = 10; } } " dcl-file)
      (write-line "    } " dcl-file)
      (write-line "    : boxed_column { label = \"중간말뚝(Post pile) 설정\"; " dcl-file)
      (write-line "      : row { " dcl-file)
      (write-line "        : toggle { key = \"chk_post_enable\"; label = \"생성 적용\"; value = \"1\"; width = 12; } " dcl-file)
      (write-line "        : popup_list { key = \"post_layout_mode\"; label = \"배치:\"; width = 16; } " dcl-file)
      (write-line "        : toggle { key = \"chk_post_invert\"; label = \"교차 반전\"; } " dcl-file)
      (write-line "      } " dcl-file)
      (write-line "      : row { " dcl-file)
      (write-line "        : radio_row { key = \"post_side_grp\"; " dcl-file)
      (write-line "          : radio_button { key = \"post_side_L\"; label = \"보강재 왼쪽\"; value = \"1\"; } " dcl-file)
      (write-line "          : radio_button { key = \"post_side_R\"; label = \"보강재 오른쪽\"; } " dcl-file)
      (write-line "        } " dcl-file)
      (write-line "      } " dcl-file)
      (write-line "      : row { alignment = right; : button { key = \"btn_post_add\"; label = \"추가\"; width = 10; } : button { key = \"btn_post_del\"; label = \"삭제\"; width = 10; } : button { key = \"btn_post_reset\"; label = \"초기화\"; width = 10; } } " dcl-file)
      (write-line "    } " dcl-file)
      (write-line "    : boxed_row {" dcl-file)
      (write-line "      label = \"코너부 띠장 상향 (Splice)\";" dcl-file)
      (write-line "      : toggle { key = \"chk_upgrade_wale\"; label = \"사보강재(Corner Strut) 구간 띠장 상향 적용\"; is_enabled = false; }" dcl-file)
      (write-line "      : popup_list { key = \"upgrade_wale_spec\"; width = 20; is_enabled = false; }" dcl-file)
      (write-line "    }" dcl-file)
      (write-line "    : spacer { height = 0.5; }" dcl-file)
      (write-line "    : row { alignment = centered; : button { key = \"btn_measure\"; label = \"도면에서 확인/측정\"; width = 25; } }" dcl-file)
      (write-line "    : spacer { height = 0.5; }" dcl-file)
      (write-line "    : row {" dcl-file)
      (write-line "      alignment = centered;" dcl-file)
      (write-line "      : button { key = \"accept\"; label = \"다음\"; width = 12; }" dcl-file)
      (write-line "      : button { key = \"btn_comp\"; label = \"완료\"; is_default = true; width = 12; }" dcl-file)
      (write-line "      : button { key = \"cancel\"; label = \"취소\"; is_cancel = true; width = 12; }" dcl-file)
      (write-line "    }" dcl-file)
      (write-line "  }" dcl-file)
      (write-line "}" dcl-file)
      
      ;; ----------------------------------------------------------------------
      ;; [DCL 8] tsp_brace_warn & tsp_brace_hard_warn : 사보강재 한계 초과 경고
      ;; ----------------------------------------------------------------------
      
      (write-line "tsp_brace_angle_warn : dialog { label = \"경고: 완만한 코너 각도\"; " dcl-file)
      (write-line "  : text { key = \"angle_msg\"; label = \"코너 각도가 120도 이상입니다.\"; alignment = centered; } " dcl-file)
      (write-line "  : text { label = \"사보강재(Corner Strut) 설치 시 부재 간 간섭이 발생할 수 있습니다.\"; alignment = centered; } " dcl-file)
      (write-line "  : spacer { height = 0.5; } " dcl-file)
      (write-line "  : row { alignment = centered; " dcl-file)
      (write-line "    : button { key = \"btn_skip\"; label = \"생략 (Skip)\"; is_default = true; is_cancel = true; width = 12; } " dcl-file)
      (write-line "    : button { key = \"btn_cont\"; label = \"계속 (Continue)\"; width = 12; } " dcl-file)
      (write-line "  } " dcl-file)
      (write-line "} " dcl-file)

      (write-line "tsp_brace_warn : dialog {" dcl-file)
      (write-line "  label = \"경고: 권장 공간 초과\";" dcl-file)
      (write-line "  : text { label = \"입력한 누적거리가 권장 한계(50%)를 초과했습니다.\"; alignment = centered; }" dcl-file)
      (write-line "  : text { label = \"이웃 모서리의 사보강재(Corner Strut) 설치 공간이 부족해질 수 있습니다.\"; alignment = centered; }" dcl-file)
      (write-line "  : text { label = \"그래도 리스트에 추가(수정)하시겠습니까?\"; alignment = centered; }" dcl-file)
      (write-line "  : spacer { height = 0.5; }" dcl-file)
      (write-line "  : row {" dcl-file)
      (write-line "    alignment = centered;" dcl-file)
      (write-line "    : button { key = \"accept\"; label = \"확인(계속)\"; is_default = true; width = 12; }" dcl-file)
      (write-line "    : button { key = \"cancel\"; label = \"취소\"; is_cancel = true; width = 12; }" dcl-file)
      (write-line "  }" dcl-file)
      (write-line "}" dcl-file)
      
      (write-line "tsp_brace_hard_warn : dialog {" dcl-file)
      (write-line "  label = \"경고: 절대 한계 초과\";" dcl-file)
      (write-line "  : text { key = \"warn_msg1\"; label = \"입력한 거리가 물리적 절대 한계를 초과했습니다!\"; alignment = centered; }" dcl-file)
      (write-line "  : text { key = \"warn_msg2\"; label = \"부재 간 간섭이 발생할 수 있습니다. 강제로 적용하시겠습니까?\"; alignment = centered; }" dcl-file)
      (write-line "  : spacer { height = 0.5; }" dcl-file)
      (write-line "  : row {" dcl-file)
      (write-line "    alignment = centered;" dcl-file)
      (write-line "    : button { key = \"accept\"; label = \"강제 적용\"; is_default = true; width = 12; }" dcl-file)
      (write-line "    : button { key = \"cancel\"; label = \"취소\"; is_cancel = true; width = 12; }" dcl-file)
      (write-line "  }" dcl-file)
      (write-line "}" dcl-file)
      
      ;; ----------------------------------------------------------------------
      ;; [DCL 9] tsp_section_mode : 세그먼트 설정
      ;; ----------------------------------------------------------------------
      (write-line "tsp_section_mode : dialog {" dcl-file)
      (write-line "  key = \"dlg_title\";" dcl-file)
      (write-line "  label = \"세그먼트 설정\";" dcl-file)
      (write-line "  : column {" dcl-file)
      (write-line "    : row {" dcl-file)
      (write-line "      : text { label = \"이름 입력 :\"; }" dcl-file)
      (write-line "      : edit_box { key = \"seg_name\"; width = 20; }" dcl-file)
      (write-line "    }" dcl-file)
      (write-line "    : spacer { height = 0.5; }" dcl-file)
      (write-line "    : row {" dcl-file)
      (write-line "      : toggle { key = \"chk_section\"; label = \"단면생성 (지반 정보 포함)\"; }" dcl-file)
      (write-line "    }" dcl-file)
      (write-line "  }" dcl-file)
      (write-line "  : spacer { height = 1; }" dcl-file)
      (write-line "  : row {" dcl-file)
      (write-line "    alignment = centered;" dcl-file)
      (write-line "    : button { key = \"accept\"; label = \"다음\"; is_default = true; width = 12; }" dcl-file)
      (write-line "    : button { key = \"cancel\"; label = \"취소\"; is_cancel = true; width = 12; }" dcl-file)
      (write-line "  }" dcl-file)
      (write-line "}" dcl-file)
      
      ;; ----------------------------------------------------------------------
      ;; [DCL 10] tsp_soil : 지반 정의
      ;; ----------------------------------------------------------------------
      (write-line "tsp_soil : dialog {" dcl-file)
      (write-line "  label = \"지반 정의\";" dcl-file)
      (write-line "  : column {" dcl-file)
      (write-line "    : text { label = \"지층 및 N치 정보를 입력하세요\"; alignment = centered; }" dcl-file)
      (write-line "    : spacer { height = 0.5; }" dcl-file)
      (write-line "    : row {" dcl-file)
      (write-line "      : edit_box { key = \"hole_no\"; label = \"HOLE No.\"; edit_width = 10; fixed_width = true; }" dcl-file)
      (write-line "      : spacer { } " dcl-file)
      (write-line "      : row { alignment = right; fixed_width = true;" dcl-file)
      (write-line "        : edit_box { key = \"soil_max_depth\"; label = \"최대굴착깊이(m)\"; edit_width = 6; fixed_width = true; }" dcl-file)
      (write-line "        : spacer { width = 1.0; fixed_width = true; }" dcl-file)
      (write-line "        : edit_box { key = \"soil_embed_depth\"; label = \"근입깊이(m)\"; edit_width = 6; fixed_width = true; }" dcl-file)
      (write-line "      }" dcl-file)
      (write-line "    }" dcl-file)
      (write-line "    : spacer { height = 0.5; }" dcl-file)
      (write-line "    : row {" dcl-file)
      (write-line "      : list_box { key = \"soil_list\"; label = \"지층 목록:\"; width = 72; height = 12; fixed_width = true; fixed_height = true; multiple_select = false; }" dcl-file)
      (write-line "      : spacer { width = 4.0; fixed_width = true; }" dcl-file)
      (write-line "      : list_box { key = \"n_val_list\"; label = \"N치 목록:\"; width = 45; height = 12; fixed_width = true; fixed_height = true; multiple_select = false; }" dcl-file)
      (write-line "    }" dcl-file)
      (write-line "    : spacer { height = 0.5; fixed_height = true; }" dcl-file)
      (write-line "    : row {" dcl-file)
      (write-line "      : column { width = 72; fixed_width = true;" dcl-file)
      (write-line "        : row {" dcl-file)
      (write-line "          : edit_box { key = \"soil_user_name\"; label = \"이름:\"; edit_width = 5; }" dcl-file)
      (write-line "          : popup_list { key = \"soil_type\"; label = \"종류:\"; edit_width = 15; }" dcl-file)
      (write-line "          : edit_box { key = \"soil_depth\"; label = \"깊이(m):\"; edit_width = 5; }" dcl-file)
      (write-line "          : edit_box { key = \"soil_phi\"; label = \"마찰각:\"; edit_width = 4; }" dcl-file)
      (write-line "        }" dcl-file)
      (write-line "      }" dcl-file)
      (write-line "      : spacer { width = 4.0; fixed_width = true; }" dcl-file)
      (write-line "      : column { width = 45; fixed_width = true;" dcl-file)
      (write-line "        : row { alignment = centered;" dcl-file)
      (write-line "          : text { label = \"N치(회/cm): \"; }" dcl-file)
      (write-line "          : edit_box { key = \"n_hit\"; edit_width = 4; fixed_width = true; }" dcl-file)
      (write-line "          : text { label = \"/\"; }" dcl-file)
      (write-line "          : edit_box { key = \"n_pen\"; edit_width = 4; fixed_width = true; }" dcl-file)
      (write-line "          : text { label = \"깊이:\"; }" dcl-file)
      (write-line "          : edit_box { key = \"n_depth\"; edit_width = 5; fixed_width = true; }" dcl-file)
      (write-line "        }" dcl-file)
      (write-line "      }" dcl-file)
      (write-line "    }" dcl-file)
      (write-line "    : spacer { height = 0.3; fixed_height = true; }" dcl-file)
      (write-line "    : row {" dcl-file)
      (write-line "      : column { width = 72; fixed_width = true;" dcl-file)
      (write-line "        : row { alignment = centered;" dcl-file)
      (write-line "          : button { key = \"btn_add\"; label = \"추가\"; width = 12; fixed_width = true; }" dcl-file)
      (write-line "          : button { key = \"btn_modify\"; label = \"수정\"; width = 12; fixed_width = true; }" dcl-file)
      (write-line "          : button { key = \"btn_delete\"; label = \"삭제\"; width = 12; fixed_width = true; }" dcl-file)
      (write-line "          : button { key = \"btn_clear\"; label = \"전체삭제\"; width = 12; fixed_width = true; }" dcl-file)
      (write-line "        }" dcl-file)
      (write-line "      }" dcl-file)
      (write-line "      : spacer { width = 4.0; fixed_width = true; }" dcl-file)
      (write-line "      : column { width = 45; fixed_width = true;" dcl-file)
      (write-line "        : row { alignment = centered;" dcl-file)
      (write-line "          : button { key = \"btn_n_add\"; label = \"추가\"; width = 10; fixed_width = true; }" dcl-file)
      (write-line "          : button { key = \"btn_n_modify\"; label = \"수정\"; width = 10; fixed_width = true; }" dcl-file)
      (write-line "          : button { key = \"btn_n_delete\"; label = \"삭제\"; width = 10; fixed_width = true; }" dcl-file)
      (write-line "          : button { key = \"btn_n_clear\"; label = \"전체삭제\"; width = 10; fixed_width = true; }" dcl-file)
      (write-line "        }" dcl-file)
      (write-line "        : spacer { height = 0.2; fixed_height = true; }" dcl-file)
      (write-line "        : row { alignment = centered;" dcl-file)
      (write-line "          : button { key = \"btn_n_get_dwg\"; label = \"도면에서 드래그하여 입력\"; width = 44; fixed_width = true; }" dcl-file)
      (write-line "        }" dcl-file)
      (write-line "        : spacer { height = 0.5; fixed_height = true; }" dcl-file)
      (write-line "        : row { alignment = centered;" dcl-file)
      (write-line "          : toggle { key = \"soil_water_chk\"; label = \"지하수위\"; }" dcl-file)
      (write-line "          : edit_box { key = \"soil_water_depth\"; label = \"GL -\"; edit_width = 8; is_enabled = false; }" dcl-file)
      (write-line "        }" dcl-file)
      (write-line "      }" dcl-file)
      (write-line "    }" dcl-file)
      (write-line "    : spacer { height = 1.0; fixed_height = true; }" dcl-file)
      (write-line "    : row {" dcl-file)
      (write-line "      : column { width = 72; fixed_width = true;" dcl-file)
      (write-line "        : boxed_column { label = \"숏크리트 설정\";" dcl-file)
      (write-line "          : row {" dcl-file)
      (write-line "            : toggle { key = \"soil_shotcrete_enable\"; label = \"숏크리트 생성\"; }" dcl-file)
      (write-line "            : spacer { width = 1.0; fixed_width = true; }" dcl-file)
      (write-line "            : edit_box { key = \"soil_shotcrete_thick\"; label = \"두께(mm)\"; edit_width = 6; }" dcl-file)
      (write-line "          }" dcl-file)
      (write-line "          : row {" dcl-file)
      (write-line "            : toggle { key = \"soil_shotcrete_chk\"; label = \"숏크리트 암반층 선택\"; }" dcl-file)
      (write-line "            : popup_list { key = \"soil_shotcrete_layer\"; edit_width = 14; is_enabled = false; }" dcl-file)
      (write-line "          }" dcl-file)
      (write-line "        }" dcl-file)
      (write-line "      }" dcl-file)
      (write-line "      : spacer { width = 4.0; fixed_width = true; }" dcl-file)
      (write-line "      : column { width = 45; fixed_width = true;" dcl-file)
      (write-line "        : boxed_column { label = \"CIP 암반 정착 설정\";" dcl-file)
      (write-line "          : row {" dcl-file)
      (write-line "            : toggle { key = \"soil_rock_embed_chk\"; label = \"CIP 암반 정착\"; }" dcl-file)
      (write-line "            : edit_box { key = \"soil_rock_embed\"; label = \"정착고(mm)\"; edit_width = 8; }" dcl-file)
      (write-line "          }" dcl-file)
      (write-line "          : row {" dcl-file)
      (write-line "            : toggle { key = \"soil_cip_rock_chk\"; label = \"CIP정착 암반층 선택\"; }" dcl-file)
      (write-line "            : popup_list { key = \"soil_cip_rock_layer\"; edit_width = 12; is_enabled = false; }" dcl-file)
      (write-line "          }" dcl-file)
      (write-line "        }" dcl-file)
      (write-line "      }" dcl-file)
      (write-line "    }" dcl-file)
      (write-line "    : spacer { height = 1.0; }" dcl-file)
      (write-line "    : row { alignment = centered;" dcl-file)
      (write-line "      : button { key = \"btn_legend\"; label = \"범례출력\"; width = 12; fixed_width = true; }" dcl-file)
      (write-line "      : button { key = \"btn_measure\"; label = \"도면에서 확인/측정\"; width = 18; fixed_width = true; }" dcl-file)
      (write-line "      : button { key = \"accept\"; label = \"확인\"; is_default = true; width = 12; }" dcl-file)
      (write-line "      : button { key = \"back\"; label = \"이전\"; width = 12; }" dcl-file)
      (write-line "      : button { key = \"cancel\"; label = \"취소\"; is_cancel = true; width = 12; }" dcl-file)
      (write-line "    }" dcl-file)
      (write-line "  }" dcl-file)
      (write-line "}" dcl-file)
      
      ;; ----------------------------------------------------------------------
      ;; [DCL 11] tsp_main : 흙막이벽 메인 메뉴
      ;; ----------------------------------------------------------------------
      (write-line "tsp_main : dialog {" dcl-file)
      (write-line "  label = \"TSP - Temporary Structure Plan\";" dcl-file)
      (write-line "  : column {" dcl-file)
      (write-line "    alignment = centered;" dcl-file)
      (write-line "    : text { label = \"흙막이벽 정의\"; alignment = centered; }" dcl-file)
      (write-line "    : spacer { height = 0.5; }" dcl-file)
      (write-line "    : button { key = \"btn_hpile\"; label = \"H-Pile + 토류판\"; width = 30; fixed_width = true; }" dcl-file)
      (write-line "    : button { key = \"btn_cip\"; label = \"C.I.P (현장타설말뚝)\"; width = 30; fixed_width = true; }" dcl-file)
      (write-line "    : button { key = \"btn_scw\"; label = \"S.C.W (소일시멘트벽)\"; width = 30; fixed_width = true; is_enabled = false; }" dcl-file)
      (write-line "    : spacer { height = 0.5; }" dcl-file)
      (write-line "    : button { key = \"back\"; label = \"이전\"; width = 12; fixed_width = true; alignment = centered; }" dcl-file)
      (write-line "    : button { key = \"cancel\"; label = \"취소\"; is_cancel = true; fixed_width = true; alignment = centered; }" dcl-file)
      (write-line "  }" dcl-file)
      (write-line "}" dcl-file)
      
      ;; ----------------------------------------------------------------------
      ;; [DCL 12] tsp_hpile : H-Pile + 토류판 설정
      ;; ----------------------------------------------------------------------
      (write-line "tsp_hpile : dialog {" dcl-file)
      (write-line "  label = \"H-Pile+토류판 설정\";" dcl-file)
      (write-line "  : column {" dcl-file)
      (write-line "    : text { label = \"H-Pile 규격\"; }" dcl-file)
      (write-line "    : popup_list { key = \"hpile_spec\"; width = 30; fixed_width = true; }" dcl-file)
      (write-line "    : row {" dcl-file)
      (write-line "      : edit_box { key = \"hpile_h\"; width = 5; is_enabled = false; }" dcl-file)
      (write-line "      : text { label = \"x\"; }" dcl-file)
      (write-line "      : edit_box { key = \"hpile_b\"; width = 5; is_enabled = false; }" dcl-file)
      (write-line "      : text { label = \"x\"; }" dcl-file)
      (write-line "      : edit_box { key = \"hpile_tw\"; width = 5; is_enabled = false; }" dcl-file)
      (write-line "      : text { label = \"/\"; }" dcl-file)
      (write-line "      : edit_box { key = \"hpile_tf\"; width = 5; is_enabled = false; }" dcl-file)
      (write-line "    }" dcl-file)
      (write-line "    : spacer { height = 0.5; }" dcl-file)
      (write-line "    : row {" dcl-file)
      (write-line "      : text { label = \"C.T.C (m)\"; width = 10; }" dcl-file)
      (write-line "      : edit_box { key = \"ctc\"; width = 5; value = \"2\"; }" dcl-file)
      (write-line "    }" dcl-file)
      (write-line "    : spacer { height = 0.5; }" dcl-file)
      (write-line "    : text { label = \"띠장 규격\"; }" dcl-file)
      (write-line "    : popup_list { key = \"wale_spec\"; width = 30; fixed_width = true; }" dcl-file)
      (write-line "    : row {" dcl-file)
      (write-line "      : edit_box { key = \"wale_h\"; width = 5; is_enabled = false; }" dcl-file)
      (write-line "      : text { label = \"x\"; }" dcl-file)
      (write-line "      : edit_box { key = \"wale_b\"; width = 5; is_enabled = false; }" dcl-file)
      (write-line "      : text { label = \"x\"; }" dcl-file)
      (write-line "      : edit_box { key = \"wale_tw\"; width = 5; is_enabled = false; }" dcl-file)
      (write-line "      : text { label = \"/\"; }" dcl-file)
      (write-line "      : edit_box { key = \"wale_tf\"; width = 5; is_enabled = false; }" dcl-file)
      (write-line "    }" dcl-file)
      (write-line "    : spacer { height = 0.5; }" dcl-file)
      (write-line "    : row {" dcl-file)
      (write-line "      : text { label = \"토류판 두께 (mm)\"; width = 10; }" dcl-file)
      (write-line "      : edit_box { key = \"timber_thickness\"; width = 5; value = \"60\"; }" dcl-file)
      (write-line "    }" dcl-file)
      (write-line "  }" dcl-file)
      (write-line "  : spacer { height = 1.0; }" dcl-file)
      (write-line "  : row {" dcl-file)
      (write-line "    alignment = centered;" dcl-file)
      (write-line "    : button { key = \"accept\"; label = \"확인\"; is_default = true; width = 12; }" dcl-file)
      (write-line "    : button { key = \"back\"; label = \"이전\"; width = 12; }" dcl-file)
      (write-line "    : button { key = \"cancel\"; label = \"취소\"; is_cancel = true; width = 12; }" dcl-file)
      (write-line "  }" dcl-file)
      (write-line "}" dcl-file)
      
      ;; ----------------------------------------------------------------------
      ;; [DCL 13] tsp_support : 지보재 정의
      ;; ----------------------------------------------------------------------
      (write-line "tsp_support : dialog {" dcl-file)
      (write-line "  label = \"지보재 정의\";" dcl-file)
      (write-line "  : column {" dcl-file)
      (write-line "    : text { label = \"지보재 목록 관리\"; alignment = centered; }" dcl-file)
      (write-line "    : spacer { height = 0.5; }" dcl-file)
      (write-line "    : list_box { key = \"support_list\"; label = \"목록:\"; width = 60; height = 12; fixed_width = true; fixed_height = true; multiple_select = false; }" dcl-file)
      (write-line "    : spacer { height = 0.5; }" dcl-file)
      (write-line "    : row {" dcl-file)
      (write-line "      : popup_list { key = \"support_type_sel\"; label = \"추가할 유형:\"; width = 20; fixed_width = true; }" dcl-file)
      (write-line "      : button { key = \"btn_add\"; label = \"추가\"; width = 10; fixed_width = true; }" dcl-file)
      (write-line "      : button { key = \"btn_modify\"; label = \"수정\"; width = 10; fixed_width = true; }" dcl-file)
      (write-line "      : button { key = \"btn_delete\"; label = \"삭제\"; width = 10; fixed_width = true; }" dcl-file)
      (write-line "      : button { key = \"btn_clear\"; label = \"전체삭제\"; width = 10; fixed_width = true; }" dcl-file)
      (write-line "    }" dcl-file)
      (write-line "  }" dcl-file)
      (write-line "  : spacer { height = 1.0; }" dcl-file)
      (write-line "  : row {" dcl-file)
      (write-line "    alignment = centered;" dcl-file)
      (write-line "    : button { key = \"accept\"; label = \"확인\"; is_default = true; width = 12; fixed_width = true; }" dcl-file)
      (write-line "    : button { key = \"back\"; label = \"이전\"; width = 12; fixed_width = true; }" dcl-file)
      (write-line "    : button { key = \"cancel\"; label = \"취소\"; is_cancel = true; width = 12; fixed_width = true; }" dcl-file)
      (write-line "  }" dcl-file)
      (write-line "}" dcl-file)
      
      ;; ----------------------------------------------------------------------
      ;; [DCL 14] tsp_support_strut : 버팀보(Strut) 입력
      ;; ----------------------------------------------------------------------
      (write-line "tsp_support_strut : dialog {" dcl-file)
      (write-line "  label = \"버팀보(Strut) 입력\";" dcl-file)
      (write-line "  : column {" dcl-file)
      (write-line "    : row {" dcl-file)
      (write-line "      : edit_box { key = \"s_name\"; label = \"이름:\"; width = 15; }" dcl-file)
      (write-line "      : popup_list { key = \"s_shape\"; label = \"형상:\"; width = 15; }" dcl-file)
      (write-line "    }" dcl-file)
      (write-line "      : row {" dcl-file)
      (write-line "        : edit_box { key = \"s_depth\"; label = \"설치깊이(m):\"; width = 10; }" dcl-file)
      (write-line "      }" dcl-file)
      (write-line "    : row {" dcl-file)
      (write-line "      : popup_list { key = \"s_mat\"; label = \"재질:\"; width = 15; }" dcl-file)
      (write-line "      : popup_list { key = \"s_sec\"; label = \"단면:\"; width = 20; }" dcl-file)
      (write-line "    }" dcl-file)
      (write-line "    : row {" dcl-file)
      (write-line "      : popup_list { key = \"s_jack\"; label = \"잭 종류:\"; width = 20; }" dcl-file)
      (write-line "    }" dcl-file)
      (write-line "    : spacer { height = 0.5; }" dcl-file)
      (write-line "    : popup_list { key = \"s_start_mode\"; label = \"작도 시작 기준:\"; width = 30; }" dcl-file)
      (write-line "    : edit_box { key = \"s_ctc\"; label = \"배열 간격 (C.T.C, m):\"; edit_width = 10; }" dcl-file)
      (write-line "    : button { key = \"btn_draw_strut\"; label = \"도면에서 직접 작도\"; }" dcl-file)
      (write-line "    : spacer { height = 0.5; }" dcl-file)
      (write-line "    : boxed_column { label = \"보강재(Brace) 설정\"; " dcl-file)
      (write-line "      : toggle { key = \"s_chk_stiffener_enable\"; label = \"보강재(Brace) 생성 적용\"; } " dcl-file)
      (write-line "      : row { : text { label = \"설계 세장비 한계:\"; width = 16; } : popup_list { key = \"s_slenderness_limit\"; width = 20; } } " dcl-file)
      (write-line "      : text { key = \"s_stiffener_info\"; label = \"최대길이: 계산 대기 | 허용: 0.0m | 0등분 | 간격: 0.0m\"; alignment = centered; } " dcl-file)
      (write-line "      : row { : toggle { key = \"s_chk_manual_interval\"; label = \"수동 간격(m):\"; width = 16; } : edit_box { key = \"s_manual_interval\"; width = 10; } } " dcl-file)
      (write-line "      : row { : text { label = \"보강재 여유장(mm) :\"; width = 16; } : edit_box { key = \"s_stiffener_margin\"; width = 10; } } " dcl-file)
      (write-line "    } " dcl-file)
      (write-line "    : boxed_column { label = \"중간말뚝(Post pile) 설정\"; " dcl-file)
      (write-line "      : row { " dcl-file)
      (write-line "        : toggle { key = \"s_chk_post_enable\"; label = \"생성 적용\"; value = \"1\"; width = 12; } " dcl-file)
      (write-line "      } " dcl-file)
      (write-line "      : row { " dcl-file)
      (write-line "        : radio_row { key = \"s_post_side_grp\"; " dcl-file)
      (write-line "          : radio_button { key = \"s_post_side_L\"; label = \"보강재 왼쪽(Top)\"; value = \"1\"; } " dcl-file)
      (write-line "          : radio_button { key = \"s_post_side_R\"; label = \"보강재 오른쪽(Bottom)\"; } " dcl-file)
      (write-line "        } " dcl-file)
      (write-line "      } " dcl-file)
      (write-line "      : row { alignment = right; : button { key = \"s_btn_post_add\"; label = \"수동추가\"; width = 10; } : button { key = \"s_btn_post_del\"; label = \"수동삭제\"; width = 10; } : button { key = \"s_btn_post_reset\"; label = \"초기화\"; width = 10; } } " dcl-file)
      (write-line "    } " dcl-file)
      (write-line "    : spacer { height = 1; }" dcl-file)
      (write-line "    : button { key = \"btn_redraw_strut\"; label = \"도면에서 확인/측정\"; }" dcl-file)
      (write-line "    : spacer { height = 1; }" dcl-file)
      (write-line "    : row {" dcl-file)
      (write-line "      alignment = centered;" dcl-file)
      (write-line "      : button { key = \"accept\"; label = \"확인\"; is_default = true; width = 12; }" dcl-file)
      (write-line "      : button { key = \"cancel\"; label = \"취소\"; is_cancel = true; width = 12; }" dcl-file)
      (write-line "    }" dcl-file)
      (write-line "  }" dcl-file)
      (write-line "}" dcl-file)
      
      ;; ----------------------------------------------------------------------
      ;; [DCL 15] tsp_support_anchor : 앵커(Earth Anchor) 입력
      ;; ----------------------------------------------------------------------
      (write-line "tsp_support_anchor : dialog {" dcl-file)
      (write-line "  label = \"앵커(Earth Anchor) 입력\";" dcl-file)
      (write-line "  : column {" dcl-file)
      (write-line "    : row {" dcl-file)
      (write-line "      : edit_box { key = \"a_name\"; label = \"이름:\"; width = 15; }" dcl-file)
      (write-line "      : popup_list { key = \"a_shape\"; label = \"형상:\"; width = 15; }" dcl-file)
      (write-line "    }" dcl-file)
      (write-line "    : row {" dcl-file)
      (write-line "      : edit_box { key = \"a_depth\"; label = \"설치깊이(m):\"; width = 10; }" dcl-file)
      (write-line "      : edit_box { key = \"a_angle\"; label = \"설치각도(도):\"; width = 5; }" dcl-file)
      (write-line "    }" dcl-file)
      (write-line "    : row {" dcl-file)
      (write-line "      : edit_box { key = \"a_free\"; label = \"자유장(m):\"; width = 10; }" dcl-file)
      (write-line "      : edit_box { key = \"a_bond\"; label = \"정착장(m):\"; width = 10; }" dcl-file)
      (write-line "    }" dcl-file)
      (write-line "    : row {" dcl-file)
      (write-line "      : popup_list { key = \"a_mat\"; label = \"재질:\"; width = 15; }" dcl-file)
      (write-line "      : popup_list { key = \"a_sec\"; label = \"단면:\"; width = 20; }" dcl-file)
      (write-line "    }" dcl-file)
      (write-line "    : spacer { height = 1; }" dcl-file)
      (write-line "    : row {" dcl-file)
      (write-line "      alignment = centered;" dcl-file)
      (write-line "      : button { key = \"accept\"; label = \"확인\"; is_default = true; width = 12; }" dcl-file)
      (write-line "      : button { key = \"cancel\"; label = \"취소\"; is_cancel = true; width = 12; }" dcl-file)
      (write-line "    }" dcl-file)
      (write-line "  }" dcl-file)
      (write-line "}" dcl-file)
      
      (close dcl-file)
      dcl-path
    )
    nil
  )
)


;;;;==========================================================================
;;;; defun tsp-create-cip-dcl : C.I.P 전용 DCL 다이얼로그 파일 생성
;;;;==========================================================================
(defun tsp-create-cip-dcl ( / dcl-file fn )
  (setq dcl-file (strcat (getvar "TEMPPREFIX") "tsp_cip.dcl"))
  (setq fn (open dcl-file "w"))
  (write-line "tsp_cip_dlg : dialog {" fn)
  (write-line "  label = \"C.I.P 설정\";" fn)
  (write-line "  : column {" fn)
  ;; 2. H-Pile 규격 및 치수 박스
  (write-line "    : text { label = \"H-Pile 규격\"; }" fn)
  (write-line "    : popup_list { key = \"cip_hpile_spec\"; width = 30; fixed_width = true; }" fn)
  (write-line "    : row {" fn)
  (write-line "      : edit_box { key = \"cip_hpile_h\"; width = 5; is_enabled = false; }" fn)
  (write-line "      : text { label = \"x\"; }" fn)
  (write-line "      : edit_box { key = \"cip_hpile_b\"; width = 5; is_enabled = false; }" fn)
  (write-line "      : text { label = \"x\"; }" fn)
  (write-line "      : edit_box { key = \"cip_hpile_tw\"; width = 5; is_enabled = false; }" fn)
  (write-line "      : text { label = \"/\"; }" fn)
  (write-line "      : edit_box { key = \"cip_hpile_tf\"; width = 5; is_enabled = false; }" fn)
  (write-line "    }" fn)
  (write-line "    : spacer { height = 0.5; }" fn)
  ;; 3. 띠장 규격 및 치수 박스
  (write-line "    : text { label = \"띠장 규격\"; }" fn)
  (write-line "    : popup_list { key = \"cip_wale_spec\"; width = 30; fixed_width = true; }" fn)
  (write-line "    : row {" fn)
  (write-line "      : edit_box { key = \"cip_wale_h\"; width = 5; is_enabled = false; }" fn)
  (write-line "      : text { label = \"x\"; }" fn)
  (write-line "      : edit_box { key = \"cip_wale_b\"; width = 5; is_enabled = false; }" fn)
  (write-line "      : text { label = \"x\"; }" fn)
  (write-line "      : edit_box { key = \"cip_wale_tw\"; width = 5; is_enabled = false; }" fn)
  (write-line "      : text { label = \"/\"; }" fn)
  (write-line "      : edit_box { key = \"cip_wale_tf\"; width = 5; is_enabled = false; }" fn)
  (write-line "    }" fn)
  (write-line "    : spacer { height = 0.5; }" fn)
  ;; 4. C.I.P 전용 배열 설정
  (write-line "    : row {" fn)
  (write-line "      : text { label = \"C.I.P 직경 (D)\"; width = 10; }" fn)
  (write-line "      : edit_box { key = \"cip_dia\"; width = 5; }" fn)
  (write-line "    }" fn)
  (write-line "    : spacer { height = 0.5; }" fn)
  (write-line "    : row {" fn)
  (write-line "      : text { label = \"배열 모드\"; width = 10; }" fn)
  (write-line "      : popup_list { key = \"cip_layout_mode\"; width = 15; }" fn)
  (write-line "      : text { label = \"겹침량(mm)\"; }" fn)
  (write-line "      : edit_box { key = \"cip_overlap\"; width = 5; }" fn)
  (write-line "    }" fn)
  (write-line "    : spacer { height = 0.5; }" fn)
  (write-line "    : row {" fn)
  (write-line "      : text { label = \"H-Pile 삽입\"; width = 10; }" fn)
  (write-line "      : popup_list { key = \"cip_interval\"; width = 15; }" fn)
  (write-line "    }" fn)
  (write-line "    : spacer { height = 0.5; }" fn)
  (write-line "    : row {" fn)
  (write-line "      : text { label = \"그라우팅 선택\"; width = 10; }" fn)
  (write-line "      : popup_list { key = \"cip_grouting\"; width = 15; }" fn)
  (write-line "    }" fn)
  (write-line "  }" fn)
  ;; 5. 하단 버튼 영역
  (write-line "  : spacer { height = 1.0; }" fn)
  (write-line "  : row {" fn)
  (write-line "    alignment = centered;" fn)
  (write-line "    : button { key = \"accept\"; label = \"확인\"; is_default = true; width = 12; }" fn)
  (write-line "    : button { key = \"back\"; label = \"이전\"; width = 12; }" fn)
  (write-line "    : button { key = \"cancel\"; label = \"취소\"; is_cancel = true; width = 12; }" fn)
  (write-line "  }" fn)
  (write-line "}" fn)
  (close fn)
  dcl-file
) 


;;;;==========================================================================
;;;; defun tsp-cip-update-hpile-dims : H-Pile 규격에 맞춰 치수 박스 및 직경(D) 자동 업데이트
;;;;==========================================================================
(defun tsp-cip-update-hpile-dims (idx-str / idx hpile-spec hpile-vals h)
  (setq idx (atoi idx-str))
  (setq hpile-spec (nth idx *tsp-std-wall-list*))
  (if hpile-spec
    (progn
      (setq hpile-vals (parse-h-spec hpile-spec))
      (setq h (nth 0 hpile-vals))
      ;; 치수 박스 표시 (비활성화 상태이므로 값만 갱신)
      (set_tile "cip_hpile_h" (itoa (nth 0 hpile-vals)))
      (set_tile "cip_hpile_b" (itoa (nth 1 hpile-vals)))
      (set_tile "cip_hpile_tw" (itoa (nth 2 hpile-vals)))
      (set_tile "cip_hpile_tf" (itoa (nth 3 hpile-vals)))
      ;; 직경(D) 자동 연동 로직
      (cond
        ((<= h 250) (set_tile "cip_dia" "450"))
        ((<= h 300) (set_tile "cip_dia" "500"))
        ((<= h 350) (set_tile "cip_dia" "600"))
        ((<= h 400) (set_tile "cip_dia" "700"))
        (t (set_tile "cip_dia" "500"))
      )
    )
  )
)


;;;;==========================================================================
;;;; defun tsp-cip-update-wale-dims : 띠장 규격에 맞춰 치수 박스 자동 업데이트
;;;;==========================================================================
(defun tsp-cip-update-wale-dims (idx-str / idx wale-spec wale-vals)
  (setq idx (atoi idx-str))
  (setq wale-spec (nth idx *tsp-std-wall-list*))
  (if wale-spec
    (progn
      (setq wale-vals (parse-h-spec wale-spec))
      (set_tile "cip_wale_h" (itoa (nth 0 wale-vals)))
      (set_tile "cip_wale_b" (itoa (nth 1 wale-vals)))
      (set_tile "cip_wale_tw" (itoa (nth 2 wale-vals)))
      (set_tile "cip_wale_tf" (itoa (nth 3 wale-vals)))
    )
  )
)


;;;;==========================================================================
;;;; defun tsp-cip-update-mode : 배열 모드 변경 시 겹침량 입력창 활성/비활성 제어
;;;;==========================================================================
(defun tsp-cip-update-mode (val)
  (if (= val "0") ; 맞닿음 (Tangent)
    (progn
      (mode_tile "cip_overlap" 1)
      (set_tile "cip_overlap" "0")
    )
    (progn ; 겹침 (Secant)
      (mode_tile "cip_overlap" 0)
      (if (or (not *tsp-cip-overlap*) (= *tsp-cip-overlap* "") (= *tsp-cip-overlap* "0"))
        (set_tile "cip_overlap" "50")
        (set_tile "cip_overlap" *tsp-cip-overlap*)
      )
    )
  )
)


;;;;==========================================================================
;;;; defun tsp-run-cip-dialog : C.I.P 설정 대화상자 실행 및 콜백 제어
;;;;==========================================================================
(defun tsp-run-cip-dialog
  ( / dcl-id dcl-file mode-list interval-list dcl-status
      bak-wall-type bak-cip-hpile-idx bak-cip-wale-idx bak-cip-dia
      bak-cip-mode-idx bak-cip-overlap bak-cip-equal-divide
      bak-cip-interval-idx bak-cip-grouting-idx sync-idx
 )
  (setq dcl-file (tsp-create-cip-dcl))
  (setq dcl-id (load_dialog dcl-file))
  (if (not (new_dialog "tsp_cip_dlg" dcl-id)) (exit))
  
  (setq bak-wall-type        *tsp-wall-type*)
  (setq bak-cip-hpile-idx    *tsp-cip-hpile-idx*)
  (setq bak-cip-wale-idx     *tsp-cip-wale-idx*)
  (setq bak-cip-dia          *tsp-cip-dia*)
  (setq bak-cip-mode-idx     *tsp-cip-mode-idx*)
  (setq bak-cip-overlap      *tsp-cip-overlap*)
  (if (not *tsp-cip-equal-divide*) (setq *tsp-cip-equal-divide* "1"))
  (setq bak-cip-equal-divide *tsp-cip-equal-divide*)
  (setq bak-cip-interval-idx *tsp-cip-interval-idx*)
  (setq bak-cip-grouting-idx *tsp-cip-grouting-idx*)
  
  (if (and *tsp-wale-spec* (setq sync-idx (vl-position *tsp-wale-spec* *tsp-std-wall-list*)))
    (setq *tsp-cip-wale-idx* (itoa sync-idx))
  )
  
  (start_list "cip_hpile_spec") (mapcar 'add_list *tsp-std-wall-list*) (end_list)
  (start_list "cip_wale_spec") (mapcar 'add_list *tsp-std-wall-list*) (end_list)
  (setq mode-list '("맞닿음 (Tangent)" "겹침 (Secant)"))
  (setq interval-list '("모든 공 삽입 (1/1)" "1공 건너 삽입 (1/2)" "2공 건너 삽입 (1/3)"))
  (setq grouting-list '("D200" "D600"))
  
  (start_list "cip_layout_mode") (mapcar 'add_list mode-list) (end_list)
  (start_list "cip_interval") (mapcar 'add_list interval-list) (end_list)
  (start_list "cip_grouting") (mapcar 'add_list grouting-list) (end_list)
  
  ;; [깊이 관련 set_tile 제거 완료]
  (set_tile "cip_hpile_spec" *tsp-cip-hpile-idx*)
  (set_tile "cip_wale_spec" *tsp-cip-wale-idx*)
  (set_tile "cip_dia" *tsp-cip-dia*)
  (set_tile "cip_layout_mode" *tsp-cip-mode-idx*)
  (set_tile "cip_overlap" *tsp-cip-overlap*)
  (set_tile "cip_equal_divide" *tsp-cip-equal-divide*)
  (set_tile "cip_interval" *tsp-cip-interval-idx*)
  (set_tile "cip_grouting" *tsp-cip-grouting-idx*)
  
  (tsp-cip-update-hpile-dims *tsp-cip-hpile-idx*)
  (tsp-cip-update-wale-dims *tsp-cip-wale-idx*)
  (tsp-cip-update-mode *tsp-cip-mode-idx*)
  
  (action_tile "cip_hpile_spec" "(tsp-cip-update-hpile-dims $value)")
  (action_tile "cip_wale_spec" "(tsp-cip-update-wale-dims $value)")
  (action_tile "cip_layout_mode" "(tsp-cip-update-mode $value)")
  
  (action_tile "back" "(progn
    (setq *tsp-wall-type* bak-wall-type)
    (setq *tsp-cip-hpile-idx* bak-cip-hpile-idx)
    (setq *tsp-cip-wale-idx* bak-cip-wale-idx)
    (setq *tsp-cip-dia* bak-cip-dia)
    (setq *tsp-cip-mode-idx* bak-cip-mode-idx)
    (setq *tsp-cip-overlap* bak-cip-overlap)
    (setq *tsp-cip-equal-divide* bak-cip-equal-divide)
    (setq *tsp-cip-interval-idx* bak-cip-interval-idx)
    (setq *tsp-cip-grouting-idx* bak-cip-grouting-idx)
    (done_dialog 2)
  )")
  
  (action_tile "cancel" "(progn
    (setq *tsp-wall-type* bak-wall-type)
    (setq *tsp-cip-hpile-idx* bak-cip-hpile-idx)
    (setq *tsp-cip-wale-idx* bak-cip-wale-idx)
    (setq *tsp-cip-dia* bak-cip-dia)
    (setq *tsp-cip-mode-idx* bak-cip-mode-idx)
    (setq *tsp-cip-overlap* bak-cip-overlap)
    (setq *tsp-cip-equal-divide* bak-cip-equal-divide)
    (setq *tsp-cip-interval-idx* bak-cip-interval-idx)
    (setq *tsp-cip-grouting-idx* bak-cip-grouting-idx)
    (done_dialog 0)
  )")
  
  (action_tile "accept" "(progn
    (setq *tsp-wall-type* \"CIP\")
    ;; [깊이 관련 get_tile 제거 완료]
    (setq *tsp-cip-hpile-idx* (get_tile \"cip_hpile_spec\"))
    
    (setq *tsp-cip-wale-idx* (get_tile \"cip_wale_spec\"))
    (setq *tsp-wale-spec* (nth (atoi *tsp-cip-wale-idx*) *tsp-std-wall-list*))
    
    (setq *tsp-cip-dia* (get_tile \"cip_dia\"))
    (setq *tsp-cip-mode-idx* (get_tile \"cip_layout_mode\"))
    (setq *tsp-cip-overlap* (get_tile \"cip_overlap\"))
    (setq *tsp-cip-equal-divide* (get_tile \"cip_equal_divide\"))
    (setq *tsp-cip-interval-idx* (get_tile \"cip_interval\"))
    (setq *tsp-cip-grouting-idx* (get_tile \"cip_grouting\"))
    (done_dialog 1)
  )")
  
  (setq dcl-status (start_dialog))
  (unload_dialog dcl-id)
  (vl-file-delete dcl-file)
  
  dcl-status
)

;;;;==========================================================================
;;;; defun section-choice-dialog-callback : 단면도 생성 시 세그먼트/모서리 선택 다이얼로그 콜백
;;;;==========================================================================
(defun section-choice-dialog-callback (dcl-path / dcl-id result draw-seg draw-cor)
  (setq dcl-id (load_dialog dcl-path))
  (if (new_dialog "tsp_section_choice" dcl-id)
    (progn
      (action_tile "accept" "(progn (setq draw-seg (= (get_tile \"chk_seg_sec\") \"1\")) (setq draw-cor (= (get_tile \"chk_cor_sec\") \"1\")) (if (or draw-seg draw-cor) (done_dialog 1) (alert \"최소 하나 이상의 단면도를 선택해야 합니다.\")))")
      (action_tile "cancel" "(done_dialog 0)")
      (setq result (start_dialog))
      (unload_dialog dcl-id)
      (if (= result 1)
        (list draw-seg draw-cor)
        nil
      )
    )
    nil
  )
)


;;;;==========================================================================
;;;; defun tsp-apply-settings-to-all : 선택한 세그먼트의 설정값을 모든 세그먼트에 일괄 적용
;;;;==========================================================================
(defun tsp-apply-settings-to-all (source-idx / source-data i new-list item new-item)
  (setq source-data (nth source-idx *segment-list*))
  (setq i 0 new-list '())
  (foreach item *segment-list*
    (if (= i source-idx)
      (setq new-list (append new-list (list item)))
      (progn
        (setq new-item (list
          (cons 'ID (cdr (assoc 'ID item)))
          (cons 'NAME (cdr (assoc 'NAME item)))
          (cons 'IS-DEFINED T)
          (cons 'WALL-TYPE (if (assoc 'WALL-TYPE source-data) (cdr (assoc 'WALL-TYPE source-data)) "HPILE"))
          (cons 'SECTION-DRAW (cdr (assoc 'SECTION-DRAW source-data)))
          (cons 'SOIL-DATA (cdr (assoc 'SOIL-DATA source-data)))
          (cons 'N-VALUES (cdr (assoc 'N-VALUES source-data)))
          (cons 'HOLE-NO (if (assoc 'HOLE-NO source-data) (cdr (assoc 'HOLE-NO source-data)) "BH-"))
          (cons 'WALL-SPEC (cdr (assoc 'WALL-SPEC source-data)))
          (cons 'WALL-CUSTOM (cdr (assoc 'WALL-CUSTOM source-data)))
          (cons 'WALE-SPEC (cdr (assoc 'WALE-SPEC source-data)))
          (cons 'WALE-CUSTOM (cdr (assoc 'WALE-CUSTOM source-data)))
          (cons 'CTC (cdr (assoc 'CTC source-data)))
          (cons 'TIMBER-THICKNESS (cdr (assoc 'TIMBER-THICKNESS source-data)))
          (cons 'MAX-DEPTH (cdr (assoc 'MAX-DEPTH source-data)))
          (cons 'EMBED-DEPTH (cdr (assoc 'EMBED-DEPTH source-data)))
          (cons 'CIP-MAX-DEPTH (if (assoc 'CIP-MAX-DEPTH source-data) (cdr (assoc 'CIP-MAX-DEPTH source-data)) "10.0"))
          (cons 'CIP-EMBED-DEPTH (if (assoc 'CIP-EMBED-DEPTH source-data) (cdr (assoc 'CIP-EMBED-DEPTH source-data)) "3.0"))
          (cons 'CIP-HPILE-IDX (if (assoc 'CIP-HPILE-IDX source-data) (cdr (assoc 'CIP-HPILE-IDX source-data)) "2"))
          (cons 'CIP-WALE-IDX (if (assoc 'CIP-WALE-IDX source-data) (cdr (assoc 'CIP-WALE-IDX source-data)) "2"))
          (cons 'CIP-DIA (if (assoc 'CIP-DIA source-data) (cdr (assoc 'CIP-DIA source-data)) "500"))
          (cons 'CIP-MODE-IDX (if (assoc 'CIP-MODE-IDX source-data) (cdr (assoc 'CIP-MODE-IDX source-data)) "0"))
          (cons 'CIP-OVERLAP (if (assoc 'CIP-OVERLAP source-data) (cdr (assoc 'CIP-OVERLAP source-data)) "0"))
          ;; [데이터 누락 방지] 스마트 분배 설정값 일괄 적용 복사 추가
          (cons 'CIP-EQUAL-DIVIDE (if (assoc 'CIP-EQUAL-DIVIDE source-data) (cdr (assoc 'CIP-EQUAL-DIVIDE source-data)) "1"))
          (cons 'CIP-INTERVAL-IDX (if (assoc 'CIP-INTERVAL-IDX source-data) (cdr (assoc 'CIP-INTERVAL-IDX source-data)) "2"))
          (cons 'CIP-GROUTING-IDX (if (assoc 'CIP-GROUTING-IDX source-data) (cdr (assoc 'CIP-GROUTING-IDX source-data)) "0"))
          (cons 'WATER-CHK (cdr (assoc 'WATER-CHK source-data)))
          (cons 'WATER-DEPTH (cdr (assoc 'WATER-DEPTH source-data)))
          (cons 'SHOTCRETE-ENABLE (if (assoc 'SHOTCRETE-ENABLE source-data) (cdr (assoc 'SHOTCRETE-ENABLE source-data)) "1"))
          (cons 'SHOTCRETE-CHK (if (assoc 'SHOTCRETE-CHK source-data) (cdr (assoc 'SHOTCRETE-CHK source-data)) "0"))
          (cons 'SHOTCRETE-LAYER (if (assoc 'SHOTCRETE-LAYER source-data) (cdr (assoc 'SHOTCRETE-LAYER source-data)) ""))
          (cons 'SHOTCRETE-THICK (if (assoc 'SHOTCRETE-THICK source-data) (cdr (assoc 'SHOTCRETE-THICK source-data)) 0.0))
          (cons 'SUPPORT-LIST (cdr (assoc 'SUPPORT-LIST source-data)))
          (cons 'CORNER-BRACE 
            (if (and (cdr (assoc 'CORNER-BRACE item)) (= (car (cdr (assoc 'CORNER-BRACE item))) "Y"))
              (cdr (assoc 'CORNER-BRACE source-data))
              (cdr (assoc 'CORNER-BRACE item))
            )
          )
          (cons 'UPGRADE-WALE (cdr (assoc 'UPGRADE-WALE item)))
          (cons 'V-START (cdr (assoc 'V-START item)))
          (cons 'V-END (cdr (assoc 'V-END item)))
          (cons 'ANGLE (cdr (assoc 'ANGLE item)))
          (cons 'LENGTH (cdr (assoc 'LENGTH item)))
        ))
        (setq new-list (append new-list (list new-item)))
      )
    )
    (setq i (1+ i))
  )
  (setq *segment-list* new-list)
  (setq *tsp-data-dirty* T)
)


;;;;==========================================================================
;;;; defun tsp-apply-soil-to-all : 선택된 세그먼트의 지반 정보 및 숏크리트 설정 일괄 적용
;;;;==========================================================================
(defun tsp-apply-soil-to-all (source-idx / source-data soil-data n-vals hole-no w-chk w-depth s-enable s-chk s-layer s-thick max-dp embed-dp rock-dp i new-list item new-item)
  (setq source-data (nth source-idx *segment-list*))
  (setq soil-data (cdr (assoc 'SOIL-DATA source-data)))
  (setq n-vals (cdr (assoc 'N-VALUES source-data)))
  (setq hole-no (if (assoc 'HOLE-NO source-data) (cdr (assoc 'HOLE-NO source-data)) "BH-"))
  (setq w-chk (cdr (assoc 'WATER-CHK source-data)))
  (setq w-depth (cdr (assoc 'WATER-DEPTH source-data)))
  (setq s-enable (cdr (assoc 'SHOTCRETE-ENABLE source-data)))
  (setq s-chk (cdr (assoc 'SHOTCRETE-CHK source-data)))
  (setq s-layer (cdr (assoc 'SHOTCRETE-LAYER source-data)))
  (setq s-thick (cdr (assoc 'SHOTCRETE-THICK source-data)))
  
  ;; [통합 깊이 변수 추출]
  (setq max-dp (cdr (assoc 'MAX-DEPTH source-data)))
  (setq embed-dp (cdr (assoc 'EMBED-DEPTH source-data)))
  (setq rock-dp (cdr (assoc 'ROCK-EMBED source-data)))
  
  (setq i 0 new-list '())
  (foreach item *segment-list*
    (if (= i source-idx)
      (setq new-list (append new-list (list item)))
      (progn
        (setq new-item item)
        (foreach key-pair (list 
            (cons 'SOIL-DATA soil-data) (cons 'N-VALUES n-vals) (cons 'HOLE-NO hole-no) 
            (cons 'WATER-CHK w-chk) (cons 'WATER-DEPTH w-depth) 
            (cons 'SHOTCRETE-ENABLE s-enable) (cons 'SHOTCRETE-CHK s-chk) 
            (cons 'SHOTCRETE-LAYER s-layer) (cons 'SHOTCRETE-THICK s-thick)
            (cons 'MAX-DEPTH max-dp) (cons 'EMBED-DEPTH embed-dp) (cons 'ROCK-EMBED rock-dp)) ;; 추가된 항목
          (if (assoc (car key-pair) new-item)
            (setq new-item (subst key-pair (assoc (car key-pair) new-item) new-item))
            (setq new-item (append new-item (list key-pair)))
          )
        )
        (setq new-list (append new-list (list new-item)))
      )
    )
    (setq i (1+ i))
  )
  (setq *segment-list* new-list)
  (setq *tsp-data-dirty* T)
)


;;;;==========================================================================
;;;; defun tsp-apply-support-to-all : 선택된 세그먼트의 지보재 정보 일괄 적용
;;;;==========================================================================
(defun tsp-apply-support-to-all (src-idx / src-data src-support i seg-data new-data)
  (setq src-data (nth src-idx *segment-list*))
  (setq src-support (cdr (assoc 'SUPPORT-LIST src-data)))
  (setq i 0)
  (setq new-data '())
  (foreach seg *segment-list*
    (if (= i src-idx)
      (setq new-data (append new-data (list seg))) ;; 원본은 그대로 유지
      (progn
        ;; 다른 세그먼트의 SUPPORT-LIST를 원본 값으로 교체
        (setq seg (subst (cons 'SUPPORT-LIST src-support) (assoc 'SUPPORT-LIST seg) seg))
        (setq new-data (append new-data (list seg)))
      )
    )
    (setq i (1+ i))
  )
  (setq *segment-list* new-data)
  (setq *tsp-data-dirty* T)
)


;;;;==========================================================================
;;;; defun tsp-reset-segment-data : 특정 세그먼트의 설정을 초기화
;;;;==========================================================================
(defun tsp-reset-segment-data (idx / old-data new-data old-brace reset-brace)
  (setq old-data (nth idx *segment-list*))
  (setq old-brace (cdr (assoc 'CORNER-BRACE old-data)))
  ;; 사보강재의 최초 기하학적 형태 판별값("Y" 또는 "N")만 추출하여 초기 상태로 롤백
  (setq reset-brace (if old-brace (list (car old-brace)) '("N")))
  
  (setq new-data (list
    (cons 'ID (cdr (assoc 'ID old-data)))
    (cons 'NAME (strcat "Seg-" (itoa (1+ idx))))
    (cons 'IS-DEFINED nil)
    (cons 'SECTION-DRAW nil)
    (cons 'SOIL-DATA nil)
    (cons 'N-VALUES nil)
    (cons 'HOLE-NO "BH-")
    (cons 'WALL-SPEC *tsp-hpile-spec*)
    (cons 'WALL-CUSTOM '(300 300 10 15))
    (cons 'WALE-SPEC *tsp-wale-spec*)
    (cons 'WALE-CUSTOM '(300 300 10 15))
    (cons 'CTC 2.0)
    (cons 'TIMBER-THICKNESS 60)
    (cons 'MAX-DEPTH 10.0)
    (cons 'EMBED-DEPTH 3.0)
    (cons 'WATER-CHK "0")
    (cons 'WATER-DEPTH 0.0)
    (cons 'SHOTCRETE-ENABLE "1")
    (cons 'SHOTCRETE-CHK "0")
    (cons 'SHOTCRETE-LAYER "")
    (cons 'SHOTCRETE-THICK 0.0)
    (cons 'SUPPORT-LIST '())
    (cons 'CORNER-BRACE reset-brace)
    (cons 'UPGRADE-WALE nil)
    (cons 'V-START (cdr (assoc 'V-START old-data)))
    (cons 'V-END (cdr (assoc 'V-END old-data)))
    (cons 'ANGLE (cdr (assoc 'ANGLE old-data)))
    (cons 'LENGTH (cdr (assoc 'LENGTH old-data)))
  ))
  (setq *segment-list* (update-list-item *segment-list* idx new-data))
  (setq *tsp-data-dirty* T)
)


;;;;==========================================================================
;;;; defun tsp-reset-all-segments : 모든 세그먼트의 설정을 일괄 초기화
;;;;==========================================================================
(defun tsp-reset-all-segments (/ i)
  (setq i 0)
  (repeat (length *segment-list*)
    (tsp-reset-segment-data i)
    (setq i (1+ i))
  )
)


;;;;==========================================================================
;;;; defun scale-dialog-callback : 스케일 설정 대화상자 콜백
;;;;==========================================================================
(defun scale-dialog-callback (dcl-path / dcl-id result s-sec s-pln)
  (setq dcl-id (load_dialog dcl-path))
  (if (new_dialog "tsp_scale" dcl-id)
    (progn
      (set_tile "scale_section" (itoa *tsp-scale-section*))
      (set_tile "scale_plan" (itoa *tsp-scale-plan*))
      (action_tile "accept"
        "(progn
           (setq s-sec (get_tile \"scale_section\"))
           (setq s-pln (get_tile \"scale_plan\"))
           (if (and (is-numeric s-sec) (is-numeric s-pln))
             (progn
               (setq *tsp-scale-section* (atoi s-sec))
               (setq *tsp-scale-plan* (atoi s-pln))
               (done_dialog 1))
             (alert \"스케일은 숫자를 입력해주세요.\")
           )
         )"
      )
      (action_tile "back" "(done_dialog 4)")
      (action_tile "cancel" "(done_dialog 0)")
      (setq result (start_dialog))
      (unload_dialog dcl-id)
      result
    )
  )
)

;;;;==========================================================================
;;;; defun project-list-callback : 프로젝트 불러오기 및 삭제 목록 팝업
;;;;==========================================================================
(defun project-list-callback (dcl-path / dcl-id result proj-list sel-idx refresh-proj-list)
  (setq dcl-id (load_dialog dcl-path))
  (setq proj-list (tsp-get-project-list))
  (if (null proj-list)
    (progn (alert "저장된 프로젝트가 없습니다.") (unload_dialog dcl-id) nil)
    (if (new_dialog "tsp_load_list" dcl-id)
      (progn
        ;; 내부 함수: 목록 새로고침


;;;;==========================================================================
;;;; defun refresh-proj-list : 자동 정리된 함수
;;;;==========================================================================
        (defun refresh-proj-list ()
          (setq proj-list (tsp-get-project-list))
          (start_list "proj_list")
          (mapcar 'add_list proj-list)
          (end_list)
        )
        (refresh-proj-list)
        (action_tile "accept"
          "(progn
             (setq sel-idx (atoi (get_tile \"proj_list\")))
             (if (and (>= sel-idx 0) (< sel-idx (length proj-list)))
               (progn
                 (tsp-load-project-data (nth sel-idx proj-list))
                 (done_dialog 1)
               )
               (alert \"불러올 목록을 선택해주세요.\")
             )
           )"
        )
        (action_tile "btn_del_proj"
          "(progn
             (setq sel-idx (atoi (get_tile \"proj_list\")))
             (if (and (>= sel-idx 0) (< sel-idx (length proj-list)))
               (progn
                 (tsp-delete-project-data (nth sel-idx proj-list))
                 (refresh-proj-list) ;; 삭제 후 목록 리프레쉬
               )
               (alert \"삭제할 목록을 선택해주세요.\")
             )
           )"
        )
        (action_tile "cancel" "(done_dialog 0)")
        (setq result (start_dialog))
        (unload_dialog dcl-id)
        (= result 1) ; 로드 성공 여부 반환 (T/nil)
      )
    )
  )
)


;;;;==========================================================================
;;;; defun main-dialog-callback : 메인 선택 대화상자 콜백
;;;;==========================================================================
(defun main-dialog-callback (dcl-path / dcl-id result)
  (setq dcl-id (load_dialog dcl-path))
  (if (new_dialog "tsp_main" dcl-id)
    (progn
      ;; [3단계] H-Pile: 즉시 "HPILE" 확정
      (action_tile "btn_hpile" "(progn (setq *tsp-wall-type* \"HPILE\") (done_dialog 1))")
      ;; [3단계] C.I.P: wall-type 건드리지 않고 step만 넘김 (확정은 CIP 다이얼로그 OK에서만)
      (action_tile "btn_cip" "(done_dialog 11)")
      (action_tile "btn_scw" "(alert \"SCW 공법은 아직 구현되지 않았습니다.\")")
      (action_tile "back" "(done_dialog 2)")
      (action_tile "cancel" "(done_dialog 0)")
      (setq result (start_dialog))
      (unload_dialog dcl-id)
      result
    )
  )
)


;;;;==========================================================================
;;;; defun update-list-item : 리스트의 특정 인덱스(idx) 요소를 new-val로 안전하게 교체
;;;;==========================================================================
(defun update-list-item (lst idx new-val / i new-list)
  (setq i 0 new-list '())
  (foreach item lst
    (if (= i idx)
      (setq new-list (append new-list (list new-val)))
      (setq new-list (append new-list (list item)))
    )
    (setq i (1+ i))
  )
  new-list
)


;;;;==========================================================================
;;;; defun input-segment-wizard : [입력 모드] 단계별 마법사 방식
;;;;==========================================================================
(defun input-segment-wizard (dcl-path idx / seg-data current-draw current-name sub-status step input-name dcl-id b-data max-limit new-brace temp-seg-data limits res cur-idx brace-loop found-valid search-idx loop-count max-loop check-b)
  (load-segment-to-globals idx)
  (setq seg-data (nth idx *segment-list*))
  (if (not (cdr (assoc 'IS-DEFINED seg-data)))
    (setq *tsp-wall-type* "HPILE")
  )
  (setq current-draw (cdr (assoc 'SECTION-DRAW seg-data)))
  (if (and (not (cdr (assoc 'IS-DEFINED seg-data)))
           *tsp-soil-layers*
           (/= *tsp-soil-layers* '()))
    (setq current-draw T)
  )
  (setq current-name (cdr (assoc 'NAME seg-data)))
  (setq b-data (cdr (assoc 'CORNER-BRACE seg-data)))
  (setq step 1)
  (while (and (>= step 1) (or (< step 7) (= step 41)))
    (setq sub-status 0)
    (cond
      ((= step 1)        (setq dcl-id (load_dialog dcl-path))
        (if (new_dialog "tsp_section_mode" dcl-id)
          (progn
            (set_tile "dlg_title" (strcat current-name " 입력 (단계별)"))
            (set_tile "seg_name" current-name)
            (set_tile "chk_section" (if current-draw "1" "0"))
            (action_tile "accept" "(setq input-name (get_tile \"seg_name\")) (setq current-draw (= (get_tile \"chk_section\") \"1\")) (done_dialog 1)")
            (action_tile "cancel" "(done_dialog 0)")
            (setq sub-status (start_dialog))
          )
        )
        (unload_dialog dcl-id)
        (if (= sub-status 1)
          (progn
            (if (and input-name (/= input-name "")) (setq current-name input-name))
            (if current-draw (setq step 2) (setq step 3))
          )
          (setq step -1)
        )
      )
      ((= step 2) (setq sub-status (soil-dialog-callback dcl-path)) (if (= sub-status 1) (setq step 3) (if (= sub-status 2) (setq step 1) (setq step -1))))
      ((= step 3)
        (setq sub-status (main-dialog-callback dcl-path))
        (cond
          ((= sub-status 1) (setq step 4))
          ((= sub-status 11) (setq step 41))
          ((= sub-status 2) (if current-draw (setq step 2) (setq step 1)))
          (t (setq step -1))
        )
      )
      ((= step 4) (setq sub-status (hpile-dialog-callback dcl-path)) (if (= sub-status 1) (setq step 5) (if (= sub-status 2) (setq step 3) (setq step -1))))
      ((= step 41) (setq sub-status (tsp-run-cip-dialog)) (if (= sub-status 1) (setq step 5) (if (= sub-status 2) (setq step 3) (setq step -1))))
      ((= step 5)
       (setq sub-status (support-dialog-callback dcl-path))
       (if (= sub-status 1)
         (if (and b-data (= (car b-data) "Y"))
           (setq step 6)
           (setq step 7))
         (if (= sub-status 2)
           (if (= *tsp-wall-type* "CIP") (setq step 41) (setq step 4))
           (setq step -1)
         )
       )
      )
      ((= step 6)
       (setq cur-idx idx)
       (setq brace-loop T)
       (while brace-loop
         (setq temp-seg-data (nth cur-idx *segment-list*))
         (setq limits (tsp-calculate-brace-limit cur-idx))
         (setq res (brace-dialog-callback dcl-path temp-seg-data limits 0))
         (if (and res (listp res))
           (progn
             (setq old-b-list (if (and (cdr (assoc 'CORNER-BRACE temp-seg-data)) (cadr (cdr (assoc 'CORNER-BRACE temp-seg-data)))) (cadr (cdr (assoc 'CORNER-BRACE temp-seg-data))) nil))
             (setq new-b-list (if (and (cadr res) (cadr (cadr res))) (cadr (cadr res)) nil))
             (setq is-dirty (not (and (equal old-b-list new-b-list) (equal (cdr (assoc 'UPGRADE-WALE temp-seg-data)) (caddr res)))))
             
             (setq b-data (cadr res))
             (setq temp-seg-data (subst (cons 'CORNER-BRACE b-data) (assoc 'CORNER-BRACE temp-seg-data) temp-seg-data))
             (setq temp-seg-data (subst (cons 'UPGRADE-WALE (caddr res)) (assoc 'UPGRADE-WALE temp-seg-data) temp-seg-data))
             (setq *segment-list* (update-list-item *segment-list* cur-idx temp-seg-data))
             
             ;; 변경사항이 있을 때만 재생성
             (if (and is-dirty *tsp-boundary-ent* *tsp-boundary-orient*)
               (tsp-redraw-realtime-plan *tsp-boundary-ent* *tsp-boundary-orient*)
             )
             (if (= (car res) "NEXT")
               (progn
                 (setq found-valid nil search-idx cur-idx loop-count 0 max-loop (length *segment-list*))
                 (while (and (not found-valid) (< loop-count max-loop))
                   (setq search-idx (1+ search-idx))
                   (if (>= search-idx max-loop)
                     (if (is-closed-polyline *tsp-boundary-ent*)
                       (setq search-idx 0)
                       (setq search-idx 9999)
                     )
                   )
                   (if (< search-idx max-loop)
                     (progn
                       (setq check-b (cdr (assoc 'CORNER-BRACE (nth search-idx *segment-list*))))
                       (if (not (and check-b (= (car check-b) "N")))
                         (setq found-valid T)
                       )
                     )
                   )
                   (setq loop-count (1+ loop-count))
                 )
                 (if found-valid
                   (setq cur-idx search-idx)
                   (progn
                     (alert "더 이상 사보강재(Corner Strut)를 입력할 유효한 모서리가 없습니다.\n입력을 완료합니다.")
                     (setq brace-loop nil)
                     (setq step 7) ; 더 이상 다음이 없으면 7단계로 이동
                   )
                 )
               )
               (progn
                 (setq brace-loop nil)
                 (setq step 7) ; COMP (완료)를 누르면 정상적으로 7단계로 이동
               )
             )
           )
           (progn 
             (setq brace-loop nil) 
             (setq step -1) ; 취소 시 마법사 종료
           )
         )
       )
      )
    )
  )
  (if (= step 7)
    (progn
      (setq seg-data (nth idx *segment-list*))
      (setq seg-data (subst (cons 'NAME current-name) (assoc 'NAME seg-data) seg-data))
      (setq seg-data (subst (cons 'SECTION-DRAW current-draw) (assoc 'SECTION-DRAW seg-data) seg-data))
      (setq *segment-list* (update-list-item *segment-list* idx seg-data))
      (sync-globals-to-segment idx)
      (setq *tsp-data-dirty* T)
    )
  )
)


;;;;==========================================================================
;;;; defun modify-segment-dashboard : [수정 모드] 통합 메뉴 대시보드 방식
;;;;==========================================================================
(defun modify-segment-dashboard (dcl-path idx / seg-data current-draw current-name loop-active menu-status input-name sub-status wall-choice dcl-id brace-data new-brace max-limit limits res cur-idx brace-loop temp-seg-data found-valid search-idx loop-count max-loop check-b)
  (load-segment-to-globals idx)
  (setq seg-data (nth idx *segment-list*))
  (setq current-draw (cdr (assoc 'SECTION-DRAW seg-data)))
  (if (and (not (cdr (assoc 'IS-DEFINED seg-data)))
           *tsp-soil-layers*
           (/= *tsp-soil-layers* '()))
    (setq current-draw T)
  )
  (setq current-name (cdr (assoc 'NAME seg-data)))
  (setq loop-active T)
  (while loop-active
    ;; 강제 자동 줌 코드 제거
    (setq seg-data (nth idx *segment-list*))
    (setq dcl-id (load_dialog dcl-path))
    (if (new_dialog "tsp_edit_menu" dcl-id)
      (progn
        (set_tile "menu_title" (strcat current-name " 설정 수정"))
        (set_tile "seg_name" current-name)
        (set_tile "chk_section" (if current-draw "1" "0"))
        (setq brace-data (cdr (assoc 'CORNER-BRACE seg-data)))
        (if brace-data
          (mode_tile "btn_brace" 0)
          (mode_tile "btn_brace" 1)
        )
        
        (action_tile "btn_soil"    "(setq current-name (get_tile \"seg_name\")) (setq current-draw (= (get_tile \"chk_section\") \"1\")) (done_dialog 2)")
        (action_tile "btn_wall"    "(setq current-name (get_tile \"seg_name\")) (setq current-draw (= (get_tile \"chk_section\") \"1\")) (done_dialog 3)")
        (action_tile "btn_support" "(setq current-name (get_tile \"seg_name\")) (setq current-draw (= (get_tile \"chk_section\") \"1\")) (done_dialog 4)")
        (action_tile "btn_brace"   "(setq current-name (get_tile \"seg_name\")) (setq current-draw (= (get_tile \"chk_section\") \"1\")) (done_dialog 5)")
        (action_tile "accept"      "(setq current-name (get_tile \"seg_name\")) (setq current-draw (= (get_tile \"chk_section\") \"1\")) (done_dialog 1)")
        (action_tile "cancel"      "(done_dialog 0)")
        (setq menu-status (start_dialog))
      )
      (setq menu-status 0)
    )
    (unload_dialog dcl-id)
    (cond
      ((= menu-status 1) (setq loop-active nil))
      ((= menu-status 0) (setq loop-active nil) (princ "\n수정이 취소되었습니다."))
      ((= menu-status 2)
       (soil-dialog-callback dcl-path)
       (if (and *tsp-soil-layers* (/= *tsp-soil-layers* '())) (setq current-draw T))
      )
      ((= menu-status 3)
       ;; [8단계] 벽체 수정 진입 시 세그먼트 저장값으로 전역 복원
       ;; → main-dialog가 현재 세그먼트의 공법(WALL-TYPE)을 기준으로 열림
       (load-segment-to-globals idx)
       (setq wall-choice (main-dialog-callback dcl-path))
       (cond
         ;; H-Pile 선택 → hpile-dialog 진행
         ((= wall-choice 1) (hpile-dialog-callback dcl-path))
         ;; C.I.P 선택 → CIP 다이얼로그 진행
         ((= wall-choice 11) (tsp-run-cip-dialog))
         ;; Back(=2) 또는 Cancel(0/-1): 전역 오염 방지를 위해 세그먼트 값 재복원
         (t (load-segment-to-globals idx))
       )
      )
      ((= menu-status 4) (support-dialog-callback dcl-path))
      ((= menu-status 5)
       (setq cur-idx idx)
       (setq brace-loop T)
       (while brace-loop
         (setq temp-seg-data (nth cur-idx *segment-list*))
         (setq limits (tsp-calculate-brace-limit cur-idx))
         (setq res (brace-dialog-callback dcl-path temp-seg-data limits 0))
         (if (and res (listp res))
           (progn
             (setq old-b-list (if (and (cdr (assoc 'CORNER-BRACE temp-seg-data)) (cadr (cdr (assoc 'CORNER-BRACE temp-seg-data)))) (cadr (cdr (assoc 'CORNER-BRACE temp-seg-data))) nil))
             (setq new-b-list (if (and (cadr res) (cadr (cadr res))) (cadr (cadr res)) nil))
             (setq is-dirty (not (and (equal old-b-list new-b-list) (equal (cdr (assoc 'UPGRADE-WALE temp-seg-data)) (caddr res)))))
             
             (setq temp-seg-data (subst (cons 'CORNER-BRACE (cadr res)) (assoc 'CORNER-BRACE temp-seg-data) temp-seg-data))
             (setq temp-seg-data (subst (cons 'UPGRADE-WALE (caddr res)) (assoc 'UPGRADE-WALE temp-seg-data) temp-seg-data))
             (setq *segment-list* (update-list-item *segment-list* cur-idx temp-seg-data))
             
             ;; 변경사항이 있을 때만 재생성
             (if (and is-dirty *tsp-boundary-ent* *tsp-boundary-orient*)
               (tsp-redraw-realtime-plan *tsp-boundary-ent* *tsp-boundary-orient*)
             )
             (if (= (car res) "NEXT")
               (progn
                 (setq found-valid nil search-idx cur-idx loop-count 0 max-loop (length *segment-list*))
                 (while (and (not found-valid) (< loop-count max-loop))
                   (setq search-idx (1+ search-idx))
                   (if (>= search-idx max-loop)
                     (if (is-closed-polyline *tsp-boundary-ent*)
                       (setq search-idx 0)
                       (setq search-idx 9999)
                     )
                   )
                   (if (< search-idx max-loop)
                     (progn
                       (setq check-b (cdr (assoc 'CORNER-BRACE (nth search-idx *segment-list*))))
                       (if (not (and check-b (= (car check-b) "N")))
                         (setq found-valid T)
                       )
                     )
                   )
                   (setq loop-count (1+ loop-count))
                 )
                 (if found-valid
                   (setq cur-idx search-idx)
                   (progn
                     (alert "더 이상 사보강재(Corner Strut)를 수정할 유효한 모서리가 없습니다.\n수정을 완료합니다.")
                     (setq brace-loop nil)
                   )
                 )
               )
               (setq brace-loop nil)
             )
           )
           (setq brace-loop nil)
         )
       )
       (setq seg-data (nth idx *segment-list*))
      )
    )
  )
  (if (= menu-status 1)
    (progn
      (setq seg-data (nth idx *segment-list*))
      (setq seg-data (subst (cons 'NAME current-name) (assoc 'NAME seg-data) seg-data))
      (setq seg-data (subst (cons 'SECTION-DRAW current-draw) (assoc 'SECTION-DRAW seg-data) seg-data))
      (setq *segment-list* (update-list-item *segment-list* idx seg-data))
      (sync-globals-to-segment idx)
      (setq *tsp-data-dirty* T)
      (princ "\n설정이 저장되었습니다.")
    )
  )
)


;;;;==========================================================================
;;;; defun format-h-spec-short : H형강 규격을 폭x높이 형태로 짧게 변환하고 2중 표기 적용 (빈 값 nil 보호 로직 추가)
;;;;==========================================================================
(defun format-h-spec-short (spec-val custom-val double-prefix / res parsed)
  (setq res "")
  (if (not spec-val) (setq spec-val "미입력")) ; 안전 가드
  (if (or (= spec-val "User-defined") (= spec-val "Custom"))
    (if custom-val
      (setq res (strcat "H " (itoa (nth 0 custom-val)) "x" (itoa (nth 1 custom-val))))
      (setq res "H 사용자정의")
    )
    (progn
      (if (and spec-val (/= spec-val "미입력"))
        (progn
          (setq parsed (parse-h-spec spec-val))
          (if parsed
             (setq res (strcat "H " (itoa (nth 0 parsed)) "x" (itoa (nth 1 parsed))))
             (setq res spec-val)
          )
        )
        (setq res spec-val)
      )
    )
  )
  (if (and double-prefix (/= res "미입력") (/= res ""))
    (setq res (strcat "2" res))
  )
  res
)


;;;;==========================================================================
;;;; defun get-segment-display-string : 세그먼트 데이터를 리스트박스 표시용 문자열로 변환
;;;;==========================================================================
(defun get-segment-display-string (idx seg-data / s-id s-name is-defined s-draw s-support wall-str support-str s-brace-data s-brace-str s-spec s-custom wall-short w-spec w-custom wale-short has-anchor-str brace-short b-row-list num-b-rows first-b-row w-type cip-dia cip-hidx-raw cip-hidx-val cip-hidx-safe cip-widx-raw cip-widx-val cip-widx-safe hole-no)
  (setq s-id (strcat (itoa (1+ idx))))
  (setq s-name (cdr (assoc 'NAME seg-data)))
  (setq is-defined (cdr (assoc 'IS-DEFINED seg-data)))
  (setq s-brace-data (cdr (assoc 'CORNER-BRACE seg-data)))
  (setq s-brace-str "")
  (if s-brace-data
    (if (= (car s-brace-data) "Y")
      (progn
        (setq b-row-list (cadr s-brace-data))
        (setq num-b-rows (length b-row-list))
        (if (> num-b-rows 0)
          (progn
            (setq first-b-row (car b-row-list))
            (setq brace-short (format-h-spec-short (car first-b-row) (cadr first-b-row) nil))
            (setq s-brace-str (strcat "Y / " (itoa num-b-rows) "열 (" brace-short ")"))
          )
          (setq s-brace-str "Y (미입력)")
        )
      )
      (setq s-brace-str "N")
    )
    (setq s-brace-str "-")
  )
  (if is-defined
    (progn
      (if (cdr (assoc 'SECTION-DRAW seg-data))
        (progn
          (setq hole-no (cdr (assoc 'HOLE-NO seg-data)))
          (if (or (null hole-no) (= hole-no "")) (setq hole-no "BH-"))
          (setq s-draw (strcat "Y(" hole-no ")"))
        )
        (setq s-draw "N")
      )
      (setq s-support (cdr (assoc 'SUPPORT-LIST seg-data)))
      (setq support-str "")
      (setq has-anchor-str nil)
      (if s-support
        (foreach item s-support
          (if (wcmatch (car item) "앵커*") (setq has-anchor-str T))
          (if (= support-str "")
            (setq support-str (car item))
            (if (not (vl-string-search (car item) support-str))
              (setq support-str (strcat support-str ", " (car item)))
            )
          )
        )
        (setq support-str "-")
      )
      ;; 벽체 타입(WALL-TYPE)에 따라 출력 텍스트 분기
      (setq w-type (cdr (assoc 'WALL-TYPE seg-data)))
      (if (not w-type) (setq w-type "HPILE")) ; 과거 데이터 호환성
      (if (= w-type "CIP")
        (progn
          ;; CIP-HPILE-IDX nil 가드 (let* 제거 → setq 순차 방식)
          (setq cip-hidx-raw (cdr (assoc 'CIP-HPILE-IDX seg-data)))
          (setq cip-hidx-val (if cip-hidx-raw (atoi cip-hidx-raw) 0))
          (setq cip-hidx-safe (if (and (>= cip-hidx-val 0) (< cip-hidx-val (length *tsp-std-wall-list*))) cip-hidx-val 0))
          (setq s-spec (nth cip-hidx-safe *tsp-std-wall-list*))
          (setq wall-short (format-h-spec-short s-spec nil nil))
          
          ;; CIP-DIA nil 가드
          (setq cip-dia (cdr (assoc 'CIP-DIA seg-data)))
          (if (not cip-dia) (setq cip-dia "450"))
          
          ;; CIP-WALE-IDX nil 가드 (let* 제거 → setq 순차 방식)
          (setq cip-widx-raw (cdr (assoc 'CIP-WALE-IDX seg-data)))
          (setq cip-widx-val (if cip-widx-raw (atoi cip-widx-raw) 0))
          (setq cip-widx-safe (if (and (>= cip-widx-val 0) (< cip-widx-val (length *tsp-std-wall-list*))) cip-widx-val 0))
          (setq w-spec (nth cip-widx-safe *tsp-std-wall-list*))
          (setq wale-short (format-h-spec-short w-spec nil has-anchor-str))
          
          (setq wall-str (strcat "D" cip-dia "(" wall-short ") / " wale-short))
          (strcat s-id "\t" s-name "\t" s-draw "\t" "C.I.P" "\t" wall-str "\t" support-str "\t" s-brace-str)
        )
        (progn ; HPILE
          (setq s-spec (cdr (assoc 'WALL-SPEC seg-data)))
          (setq s-custom (cdr (assoc 'WALL-CUSTOM seg-data)))
          (setq wall-short (format-h-spec-short s-spec s-custom nil))
          (setq w-spec (cdr (assoc 'WALE-SPEC seg-data)))
          (setq w-custom (cdr (assoc 'WALE-CUSTOM seg-data)))
          (setq wale-short (format-h-spec-short w-spec w-custom has-anchor-str))
          (setq wall-str (strcat wall-short " / " wale-short))
          (strcat s-id "\t" s-name "\t" s-draw "\t" "H-Pile+토류판" "\t" wall-str "\t" support-str "\t" s-brace-str)
        )
      )
    )
    ;; 미정의 세그먼트
    (progn
      (setq w-type (cdr (assoc 'WALL-TYPE seg-data)))
      (if (not w-type) (setq w-type "HPILE"))
      (strcat s-id "\t" s-name "\t" "-" "\t" "" "\t" "" "\t" "-" "\t" s-brace-str)
    )
  )
)


;;;;==========================================================================
;;;; defun reset-globals-to-defaults : 입력 버튼 클릭 시 전역 변수를 시스템 기본값으로 초기화
;;;;==========================================================================
(defun reset-globals-to-defaults ()
  ;; [1단계 고정] 공법 타입을 항상 HPILE로 초기화
  ;; C.I.P는 사용자가 다이얼로그에서 최종 OK를 눌렀을 때만 "CIP"로 변경됨
  (setq *tsp-wall-type* "HPILE")
  (setq *tsp-hpile-spec* (nth 0 *tsp-std-wall-list*))
  (setq *tsp-hpile-custom* '(250 250 9 14))
  (setq *tsp-wale-spec* (nth 1 *tsp-std-wall-list*))
  (setq *tsp-wale-custom* '(300 300 10 15))
  (setq *tsp-ctc* 2.0)
  (setq *tsp-timber-thickness* 60)
  
  ;; [통합된 깊이 변수 초기화]
  (setq *tsp-max-depth* 10.0)
  (setq *tsp-embed-depth* 3.0)
  (setq *tsp-rock-embed* "500") ;; 암반 하부 근입 (기본값 문자열)
  
  (setq *tsp-soil-layers* '())
  (setq *tsp-water-chk* "0")
  (setq *tsp-water-depth* 0.0)
  (setq *tsp-shotcrete-enable* "1")
  (setq *tsp-shotcrete-chk* "0")
  (setq *tsp-shotcrete-layer* "")
  (setq *tsp-shotcrete-thick* 0.0)
  (setq *tsp-support-list* '())
)

;;;;==========================================================================
;;;; defun update-segment-manager-list : 관리자 리스트박스 갱신
;;;;==========================================================================
(defun update-segment-manager-list ()
  (start_list "seg_list")
  (setq i 0)
  (foreach seg *segment-list*
    (add_list (get-segment-display-string i seg))
    (setq i (1+ i))
  )
  (end_list)
)


;;;;==========================================================================
;;;; defun sync-globals-to-segment : 전역 변수(DCL입력값)를 세그먼트 데이터 리스트로 저장
;;;;==========================================================================
(defun sync-globals-to-segment (idx / old-data new-data)
  (setq old-data (nth idx *segment-list*))
  (setq new-data (list
    (cons 'ID (cdr (assoc 'ID old-data)))
    (cons 'NAME (cdr (assoc 'NAME old-data)))
    (cons 'IS-DEFINED T)
    (cons 'WALL-TYPE (if *tsp-wall-type* *tsp-wall-type* "HPILE"))
    (cons 'SECTION-DRAW (cdr (assoc 'SECTION-DRAW old-data)))
    (cons 'SOIL-DATA *tsp-soil-layers*)
    (cons 'N-VALUES *tsp-n-values*)
    (cons 'HOLE-NO *tsp-hole-no*)
    (cons 'WALL-SPEC *tsp-hpile-spec*)
    (cons 'WALL-CUSTOM *tsp-hpile-custom*)
    (cons 'WALE-SPEC *tsp-wale-spec*)
    (cons 'WALE-CUSTOM *tsp-wale-custom*)
    (cons 'CTC *tsp-ctc*)
    (cons 'TIMBER-THICKNESS *tsp-timber-thickness*)
    
    ;; [통합된 깊이 데이터 저장]
    (cons 'MAX-DEPTH *tsp-max-depth*)
    (cons 'EMBED-DEPTH *tsp-embed-depth*)
    (cons 'ROCK-EMBED *tsp-rock-embed*)
    
    ;; === [6단계] C.I.P 전용 데이터 저장 (깊이 관련 제외) ===
    (cons 'CIP-HPILE-IDX *tsp-cip-hpile-idx*)
    (cons 'CIP-WALE-IDX *tsp-cip-wale-idx*)
    (cons 'CIP-DIA *tsp-cip-dia*)
    (cons 'CIP-MODE-IDX *tsp-cip-mode-idx*)
    (cons 'CIP-OVERLAP *tsp-cip-overlap*)
    (cons 'CIP-EQUAL-DIVIDE *tsp-cip-equal-divide*)
    (cons 'CIP-INTERVAL-IDX *tsp-cip-interval-idx*)
    (cons 'CIP-GROUTING-IDX *tsp-cip-grouting-idx*)
    
    (cons 'WATER-CHK *tsp-water-chk*)
    (cons 'WATER-DEPTH *tsp-water-depth*)
    (cons 'SHOTCRETE-ENABLE *tsp-shotcrete-enable*)
    (cons 'SHOTCRETE-CHK *tsp-shotcrete-chk*)
    (cons 'SHOTCRETE-LAYER *tsp-shotcrete-layer*)
    (cons 'SHOTCRETE-THICK *tsp-shotcrete-thick*)
    (cons 'SUPPORT-LIST *tsp-support-list*)
    (cons 'CORNER-BRACE (cdr (assoc 'CORNER-BRACE old-data)))
    (cons 'UPGRADE-WALE (cdr (assoc 'UPGRADE-WALE old-data)))
    (cons 'V-START (cdr (assoc 'V-START old-data)))
    (cons 'V-END (cdr (assoc 'V-END old-data)))
    (cons 'ANGLE (cdr (assoc 'ANGLE old-data)))
    (cons 'LENGTH (cdr (assoc 'LENGTH old-data)))
  ))
  (setq *segment-list* (update-list-item *segment-list* idx new-data))
)


;;;;==========================================================================
;;;; defun load-segment-to-globals : 세그먼트 데이터를 전역 변수로 복원
;;;;==========================================================================
(defun load-segment-to-globals (idx / seg-data val old-val)
  (setq seg-data (nth idx *segment-list*))
  (setq *tsp-current-seg-idx* idx)
  
  (if (cdr (assoc 'IS-DEFINED seg-data))
    (progn
      (setq val (cdr (assoc 'WALL-TYPE seg-data)))
      (setq *tsp-wall-type* (if val val "HPILE"))
      (setq *tsp-soil-layers* (cdr (assoc 'SOIL-DATA seg-data)))
      (setq val (cdr (assoc 'N-VALUES seg-data)))
      (setq *tsp-n-values* (if val val '()))
      (setq val (cdr (assoc 'HOLE-NO seg-data)))
      (setq *tsp-hole-no* (if val val "BH-"))
      (setq *tsp-hpile-spec* (cdr (assoc 'WALL-SPEC seg-data)))
      (setq *tsp-hpile-custom* (cdr (assoc 'WALL-CUSTOM seg-data)))
      (setq *tsp-wale-spec* (cdr (assoc 'WALE-SPEC seg-data)))
      (setq *tsp-wale-custom* (cdr (assoc 'WALE-CUSTOM seg-data)))
      (setq *tsp-ctc* (cdr (assoc 'CTC seg-data)))
      (setq *tsp-support-list* (cdr (assoc 'SUPPORT-LIST seg-data)))
      (setq val (cdr (assoc 'TIMBER-THICKNESS seg-data)))
      (setq *tsp-timber-thickness* (if val val 60))
      
      ;; [통합 깊이 변수 복원 및 구버전 데이터 호환 로직]
      (setq val (cdr (assoc 'MAX-DEPTH seg-data)))
      (setq old-val (cdr (assoc 'CIP-MAX-DEPTH seg-data)))
      (setq *tsp-max-depth* (cond (val val) (old-val (atof old-val)) (T 10.0)))

      (setq val (cdr (assoc 'EMBED-DEPTH seg-data)))
      (setq old-val (cdr (assoc 'CIP-EMBED-DEPTH seg-data)))
      (setq *tsp-embed-depth* (cond (val val) (old-val (atof old-val)) (T 3.0)))

      (setq val (cdr (assoc 'ROCK-EMBED seg-data)))
      (setq old-val (cdr (assoc 'CIP-ROCK-EMBED seg-data)))
      (setq *tsp-rock-embed* (cond (val val) (old-val old-val) (T "500")))
      
      ;; === [6단계] C.I.P 전용 데이터 복원 ===
      (setq val (cdr (assoc 'CIP-HPILE-IDX seg-data)))
      (setq *tsp-cip-hpile-idx* (if val val "2"))
      (setq val (cdr (assoc 'CIP-WALE-IDX seg-data)))
      (setq *tsp-cip-wale-idx* (if val val "0"))
      (setq val (cdr (assoc 'CIP-DIA seg-data)))
      (setq *tsp-cip-dia* (if val val "500"))
      (setq val (cdr (assoc 'CIP-MODE-IDX seg-data)))
      (setq *tsp-cip-mode-idx* (if val val "0"))
      (setq val (cdr (assoc 'CIP-OVERLAP seg-data)))
      (setq *tsp-cip-overlap* (if val val "0"))
      (setq val (cdr (assoc 'CIP-INTERVAL-IDX seg-data)))
      (setq *tsp-cip-interval-idx* (if val val "2"))
      (setq val (cdr (assoc 'CIP-GROUTING-IDX seg-data)))
      (setq *tsp-cip-grouting-idx* (if val val "0"))
      
      ;; === 수위 및 숏크리트 복원 ===
      (setq val (cdr (assoc 'WATER-CHK seg-data)))
      (setq *tsp-water-chk* (if val val "0"))
      (setq val (cdr (assoc 'WATER-DEPTH seg-data)))
      (setq *tsp-water-depth* (if val val 0.0))
      (setq val (cdr (assoc 'SHOTCRETE-CHK seg-data)))
      (setq *tsp-shotcrete-chk* (if val val "0"))
      (setq val (cdr (assoc 'SHOTCRETE-LAYER seg-data)))
      (setq *tsp-shotcrete-layer* (if val val ""))
      (setq val (cdr (assoc 'SHOTCRETE-THICK seg-data)))
      (setq *tsp-shotcrete-thick* (if val val 0.0))
      (setq val (cdr (assoc 'SHOTCRETE-ENABLE seg-data)))
      (setq *tsp-shotcrete-enable* (if val val "1"))
    )
  )
)


;;;;==========================================================================
;;;; defun tsp-parse-space-string : 띄어쓰기로 구분된 문자열을 정수 리스트로 변환 (다중 선택 처리용)
;;;;==========================================================================
(defun tsp-parse-space-string (str / lst pos)
  (setq lst '())
  (while (setq pos (vl-string-search " " str))
    (setq lst (append lst (list (atoi (substr str 1 pos)))))
    (setq str (substr str (+ pos 2)))
  )
  (if (> (strlen str) 0)
    (setq lst (append lst (list (atoi str))))
  )
  lst
)


;;;;==========================================================================
;;;; defun tsp-join-space-string : 정수 리스트를 띄어쓰기로 구분된 문자열로 변환 (다중 선택 UI 복원용)
;;;;==========================================================================
(defun tsp-join-space-string (lst / str)
  (setq str "")
  (foreach x lst
    (if (= str "")
      (setq str (itoa x))
      (setq str (strcat str " " (itoa x)))
    )
  )
  str
)


;;;;==========================================================================
;;;; defun tsp-pause-for-measurement : DCL 창을 임시로 숨기고 도면을 제어/측정할 수 있게 해주는 기능
;;;;==========================================================================
(defun tsp-pause-for-measurement (/ dist old-err)
  (princ "\n==================================================")
  (princ "\n[도면 확인 모드] 마우스 휠로 줌(Zoom) / 초점이동(Pan)이 가능합니다.")
  (princ "\n거리를 측정하려면 두 점을 클릭하시고, 확인만 하려면 ESC 또는 Enter를 누르세요.")
  (princ "\n==================================================")

  ;; 에러 처리 (사용자가 ESC를 누를 경우 명령이 완전히 종료되지 않고 DCL로 안전하게 복귀하도록 보호)
  (setq old-err *error*)
  (defun *error* (msg)
    (princ "\n측정이 취소되었습니다. 설정창으로 복귀합니다...")
    (setq *error* old-err)
    (princ)
  )

  ;; 오토캐드 기본 거리 측정 기능 실행
  (setq dist (vl-catch-all-apply 'getdist '("\n측정할 첫 번째 점을 클릭하세요 (측정종료 및 복귀: ESC 또는 Enter): ")))

  ;; 결과 출력
  (if (and dist (not (vl-catch-all-error-p dist)))
    (progn
      (princ (strcat "\n▶ 측정된 거리: " (rtos dist 2 3) " (화면을 충분히 확인하셨으면 DCL창이 다시 뜹니다)"))
    )
    (princ "\n▶ 도면 확인 종료. 설정창으로 복귀합니다...")
  )

 (setq *error* old-err)
  
  (setvar "cmdecho" 1)
  (princ)
)


;;;;==========================================================================
;;;; defun manager-dialog-callback : [메인] 다중 선택(Multi-Select) 설정 가져오기 및 초기화 로직 적용
;;;;==========================================================================
(defun manager-dialog-callback (dcl-path / dcl-id result paste-mode apply-all-mode apply-soil-mode apply-support-mode source-idx target-idx source-data target-data loop-active status-msg-text is-def max-idx check-data new-target load-result saved-list clicked-idx save-opt new-name selected-indices target-indices)
  (setq selected-idx 0)
  (setq selected-indices '(0)) ;; 다중 선택 저장용 리스트
  
  ;; 모드 플래그 초기화
  (setq paste-mode nil)
  (setq apply-all-mode nil)
  (setq apply-soil-mode nil)
  (setq apply-support-mode nil)
  (setq apply-wall-mode nil)
  (setq apply-brace-mode nil)
  (setq loop-active T)
  (setq status-msg-text "Shift 또는 Ctrl 키를 이용해 여러 개를 동시에 선택할 수 있습니다.")
  
  (while loop-active
    (setq dcl-id (load_dialog dcl-path))
    (if (new_dialog "tsp_manager" dcl-id "" '(50 50))
      (progn
        (setq saved-list (tsp-get-project-list))
        (if (or (null *tsp-current-project-name*) (= *tsp-current-project-name* ""))
          (setq *tsp-current-project-name* (tsp-generate-default-project-name))
        )
        (set_tile "manager_title" (strcat "세그먼트 설정 (Segment Manager) - " *tsp-current-project-name*))
        (set_tile "project_name" *tsp-current-project-name*)
        (update-segment-manager-list)
        ;; [핵심] 이전 다중 선택 상태를 그대로 문자열로 엮어 리스트 UI에 복원
        (set_tile "seg_list" (tsp-join-space-string selected-indices))
        (set_tile "status_msg" status-msg-text)

        (action_tile "project_name" "(set_tile \"manager_title\" (strcat \"세그먼트 설정 (Segment Manager) - \" $value))")
        (action_tile "btn_save_proj"
          "(progn
              (setq save-opt (save-prompt-dialog-callback dcl-path))
              ;; 저장 전, 화면에 입력된 최신 이름을 미리 확보합니다.
              (setq new-name (get_tile \"project_name\"))
              (if (or (= new-name \"\") (= new-name nil)) (setq new-name (tsp-generate-default-project-name)))

              (cond
                ((= save-opt 1) ;; 새로 저장
                 (tsp-save-project-data new-name)
                 (set_tile \"project_name\" *tsp-current-project-name*)
                 (set_tile \"manager_title\" (strcat \"세그먼트 설정 (Segment Manager) - \" *tsp-current-project-name*))
                 (setq *tsp-data-dirty* nil)
                 (alert (strcat \"'\" *tsp-current-project-name* \"' (으)로 새로 저장되었습니다.\"))
                )
                ((= save-opt 2) ;; 덮어쓰기
                 ;; 이름이 바뀌었다면 자동으로 새 이름으로 저장되고, 이름이 같다면 기존 파일에 덮어씌워집니다.
                 (tsp-save-project-data new-name)
                 (set_tile \"project_name\" *tsp-current-project-name*)
                 (set_tile \"manager_title\" (strcat \"세그먼트 설정 (Segment Manager) - \" *tsp-current-project-name*))
                 (setq *tsp-data-dirty* nil)
                 (alert (strcat \"'\" *tsp-current-project-name* \"' 에 저장이 완료되었습니다.\"))
                )
                (t (princ \"\\n저장이 취소되었습니다.\") )
              )
            )"
        )
        (action_tile "btn_load_proj"
          "(progn
             (setq load-result (project-list-callback dcl-path))
             (if load-result
               (progn
                 (set_tile \"project_name\" *tsp-current-project-name*)
                 (set_tile \"manager_title\" (strcat \"세그먼트 설정 (Segment Manager) - \" *tsp-current-project-name*))
                 (update-segment-manager-list)
                 (alert (strcat \"프로젝트 [\" *tsp-current-project-name* \"] 가 로드되었습니다.\"))
                 (setq *tsp-data-dirty* nil)
                 (done_dialog 12)
               )
             )
           )"
        )
        
        ;; 다중 선택 문자열($value)을 파싱하여 타겟 인덱스들 확보
        (action_tile "seg_list"
          "(progn
             (setq selected-indices (tsp-parse-space-string $value))
             (if (null selected-indices) (setq selected-indices (list 0)))
             (setq clicked-idx (car selected-indices)) ; 기본적으로 첫 번째 선택 항목을 대표로 사용
             (cond
               (paste-mode
                 (setq source-idx clicked-idx)
                 (if (member source-idx target-indices)
                   (alert \"대상 세그먼트 자체를 원본으로 지정할 수 없습니다.\\n원본 데이터를 가진 '다른 세그먼트'를 클릭하세요.\")
                   (done_dialog 3)
                 )
               )
               (apply-all-mode
                 (setq selected-idx clicked-idx)
                 (done_dialog 7)
               )
               (apply-soil-mode
                 (setq selected-idx clicked-idx)
                 (done_dialog 8)
               )
               (apply-support-mode
                 (setq selected-idx clicked-idx)
                 (done_dialog 11)
               )
               (apply-wall-mode
                 (setq selected-idx clicked-idx)
                 (done_dialog 14)
               )
               (apply-brace-mode
                 (setq selected-idx clicked-idx)
                 (done_dialog 15)
               )
               (T
                 (setq selected-idx clicked-idx)
                 (if (> (length selected-indices) 1)
                   (set_tile \"status_msg\" (strcat (itoa (length selected-indices)) \"개의 세그먼트가 선택되었습니다. (다중 선택 됨)\"))
                   (set_tile \"status_msg\" (strcat (itoa (1+ selected-idx)) \"번 목록이 선택되었습니다.\"))
                 )
               )
             )
           )"
        )

        (action_tile "btn_input" "(done_dialog 4)")
        (action_tile "btn_modify"
          "(progn
             (setq check-data (nth selected-idx *segment-list*))
             (if (cdr (assoc 'IS-DEFINED check-data))
               (done_dialog 2)
               (alert \"아직 입력되지 않은 목록입니다.\\n먼저 [입력] 버튼을 눌러 초기 설정을 진행하세요.\")))")
        (action_tile "btn_delete" "(done_dialog 9)")
        (action_tile "btn_delete_all" "(done_dialog 10)")
        
        ;; 버튼 클릭 시 타겟 인덱스들을 메모리에 저장하고 원본 선택 모드로 전환
        (action_tile "btn_copy_from"
          "(progn
             (setq paste-mode T apply-all-mode nil apply-soil-mode nil apply-support-mode nil apply-wall-mode nil apply-brace-mode nil)
             (setq target-indices selected-indices)
             (set_tile \"status_msg\" (strcat \"[다중 복사 준비 완료] 복사해 올 '원본' 세그먼트 1개를 위 목록에서 클릭하세요.\")))
          "
        )
        (action_tile "btn_apply_all"
          "(progn
             (setq apply-all-mode T paste-mode nil apply-soil-mode nil apply-support-mode nil apply-wall-mode nil apply-brace-mode nil)
             (set_tile \"status_msg\" \"[전체 일괄적용] 원본 세그먼트를 클릭하세요. (취소: ESC)\"))")
        (action_tile "btn_apply_soil"
          "(progn
             (setq apply-soil-mode T paste-mode nil apply-all-mode nil apply-support-mode nil apply-wall-mode nil apply-brace-mode nil)
             (set_tile \"status_msg\" \"[지반 일괄적용] 지반 정보를 가진 원본 세그먼트를 클릭하세요. (취소: ESC)\"))")
        (action_tile "btn_apply_support"
          "(progn
             (setq apply-support-mode T paste-mode nil apply-all-mode nil apply-soil-mode nil apply-wall-mode nil apply-brace-mode nil)
             (set_tile \"status_msg\" \"[지보재 일괄적용] 지보재 정보를 가진 원본 세그먼트를 클릭하세요. (취소: ESC)\"))")
        (action_tile "btn_apply_wall"
          "(progn
             (setq apply-wall-mode T paste-mode nil apply-all-mode nil apply-soil-mode nil apply-support-mode nil apply-brace-mode nil)
             (set_tile \"status_msg\" \"[흙막이벽 일괄적용] 흙막이벽 정보를 가진 원본 세그먼트를 클릭하세요. (취소: ESC)\"))")
        (action_tile "btn_apply_brace"
          "(progn
             (setq apply-brace-mode T paste-mode nil apply-all-mode nil apply-soil-mode nil apply-support-mode nil apply-wall-mode nil)
             (set_tile \"status_msg\" \"[사보강재 일괄적용] 사보강재 정보를 가진 원본 세그먼트를 클릭하세요. (취소: ESC)\"))")
        
        (action_tile "btn_measure" "(done_dialog 13)")

        (action_tile "btn_draw_section"
          "(progn
             (setq check-data (nth selected-idx *segment-list*))
             (if (cdr (assoc 'IS-DEFINED check-data))
               (progn
                 (load-segment-to-globals selected-idx)
                 (setq *tsp-target-draw-flag* (cdr (assoc 'SECTION-DRAW check-data)))
                 (done_dialog 5))
               (alert \"입력되지 않은 목록입니다.\")))")
        (action_tile "btn_draw_plan"
          "(progn
             (setq check-data (nth selected-idx *segment-list*))
             (if (cdr (assoc 'IS-DEFINED check-data))
               (progn (load-segment-to-globals selected-idx) (done_dialog 6))
               (alert \"입력되지 않은 목록입니다.\")))")
        (action_tile "cancel" "(done_dialog 0)")

        (setq result (start_dialog))
      )
      (setq result 0)
    )
    (unload_dialog dcl-id)

    (cond
      ((= result 0)
       (if (or paste-mode apply-all-mode apply-soil-mode apply-support-mode apply-wall-mode apply-brace-mode)
         (progn
           (setq paste-mode nil apply-all-mode nil apply-soil-mode nil apply-support-mode nil apply-wall-mode nil apply-brace-mode nil)
           (setq status-msg-text "작업이 취소되었습니다.")
           (setq loop-active T)
         )
         (setq loop-active nil)
       )
      )
      ((= result 5) (setq loop-active nil))
      ((= result 6) (setq loop-active nil))
      ((= result 4)
       (reset-globals-to-defaults)
       (input-segment-wizard dcl-path selected-idx)
       (setq max-idx (1- (length *segment-list*)))
       (if (< selected-idx max-idx) (setq selected-idx (1+ selected-idx)))
       (setq selected-indices (list selected-idx))
       (setq status-msg-text (strcat (itoa (1+ selected-idx)) "번 목록이 선택되었습니다."))
       (setq paste-mode nil apply-all-mode nil apply-soil-mode nil apply-support-mode nil)
       (if (and *tsp-boundary-ent* *tsp-boundary-orient*)
         (progn
           (load-segment-to-globals selected-idx)
           (tsp-redraw-realtime-plan *tsp-boundary-ent* *tsp-boundary-orient*)
         )
       )
      )
      ((= result 2)
       (modify-segment-dashboard dcl-path selected-idx)
       (setq selected-indices (list selected-idx))
       (setq status-msg-text "수정이 완료되었습니다.")
       (setq paste-mode nil apply-all-mode nil apply-soil-mode nil apply-support-mode nil)
       (if (and *tsp-boundary-ent* *tsp-boundary-orient*)
         (progn
           (load-segment-to-globals selected-idx)
           (tsp-redraw-realtime-plan *tsp-boundary-ent* *tsp-boundary-orient*)
         )
       )
      )
      
      ;; 다중 선택된 타겟(target-indices) 전체를 순회하며 원본 데이터를 폭격하듯 한꺼번에 덮어씌움
      ((= result 3)
       (setq source-data (nth source-idx *segment-list*))
       (if (cdr (assoc 'IS-DEFINED source-data))
         (progn
           (foreach t-idx target-indices
             (setq target-data (nth t-idx *segment-list*))
             (setq new-target (list
               (cons 'ID (cdr (assoc 'ID target-data)))
               (cons 'NAME (cdr (assoc 'NAME target-data)))
               (cons 'IS-DEFINED (cdr (assoc 'IS-DEFINED source-data)))
               (cons 'WALL-TYPE (if (assoc 'WALL-TYPE source-data) (cdr (assoc 'WALL-TYPE source-data)) "HPILE"))
               (cons 'SECTION-DRAW (cdr (assoc 'SECTION-DRAW source-data)))
               (cons 'SOIL-DATA (cdr (assoc 'SOIL-DATA source-data)))
               (cons 'N-VALUES (cdr (assoc 'N-VALUES source-data)))
               (cons 'HOLE-NO (if (assoc 'HOLE-NO source-data) (cdr (assoc 'HOLE-NO source-data)) "BH-"))
               (cons 'WALL-SPEC (cdr (assoc 'WALL-SPEC source-data)))
               (cons 'WALL-CUSTOM (cdr (assoc 'WALL-CUSTOM source-data)))
               (cons 'WALE-SPEC (cdr (assoc 'WALE-SPEC source-data)))
               (cons 'WALE-CUSTOM (cdr (assoc 'WALE-CUSTOM source-data)))
               (cons 'CTC (cdr (assoc 'CTC source-data)))
               (cons 'TIMBER-THICKNESS (cdr (assoc 'TIMBER-THICKNESS source-data)))
               (cons 'MAX-DEPTH (cdr (assoc 'MAX-DEPTH source-data)))
               (cons 'EMBED-DEPTH (cdr (assoc 'EMBED-DEPTH source-data)))
               (cons 'CIP-MAX-DEPTH (if (assoc 'CIP-MAX-DEPTH source-data) (cdr (assoc 'CIP-MAX-DEPTH source-data)) "10.0"))
               (cons 'CIP-EMBED-DEPTH (if (assoc 'CIP-EMBED-DEPTH source-data) (cdr (assoc 'CIP-EMBED-DEPTH source-data)) "3.0"))
               (cons 'CIP-HPILE-IDX (if (assoc 'CIP-HPILE-IDX source-data) (cdr (assoc 'CIP-HPILE-IDX source-data)) "2"))
               (cons 'CIP-WALE-IDX (if (assoc 'CIP-WALE-IDX source-data) (cdr (assoc 'CIP-WALE-IDX source-data)) "2"))
               (cons 'CIP-DIA (if (assoc 'CIP-DIA source-data) (cdr (assoc 'CIP-DIA source-data)) "500"))
               (cons 'CIP-MODE-IDX (if (assoc 'CIP-MODE-IDX source-data) (cdr (assoc 'CIP-MODE-IDX source-data)) "0"))
               (cons 'CIP-OVERLAP (if (assoc 'CIP-OVERLAP source-data) (cdr (assoc 'CIP-OVERLAP source-data)) "0"))
               (cons 'CIP-INTERVAL-IDX (if (assoc 'CIP-INTERVAL-IDX source-data) (cdr (assoc 'CIP-INTERVAL-IDX source-data)) "2"))
               (cons 'CIP-GROUTING-IDX (if (assoc 'CIP-GROUTING-IDX source-data) (cdr (assoc 'CIP-GROUTING-IDX source-data)) "0"))
               (cons 'WATER-CHK (cdr (assoc 'WATER-CHK source-data)))
               (cons 'WATER-DEPTH (cdr (assoc 'WATER-DEPTH source-data)))
               (cons 'SHOTCRETE-ENABLE (if (assoc 'SHOTCRETE-ENABLE source-data) (cdr (assoc 'SHOTCRETE-ENABLE source-data)) "1"))
               (cons 'SHOTCRETE-CHK (if (assoc 'SHOTCRETE-CHK source-data) (cdr (assoc 'SHOTCRETE-CHK source-data)) "0"))
               (cons 'SHOTCRETE-LAYER (if (assoc 'SHOTCRETE-LAYER source-data) (cdr (assoc 'SHOTCRETE-LAYER source-data)) ""))
               (cons 'SHOTCRETE-THICK (if (assoc 'SHOTCRETE-THICK source-data) (cdr (assoc 'SHOTCRETE-THICK source-data)) 0.0))
               (cons 'SUPPORT-LIST (cdr (assoc 'SUPPORT-LIST source-data)))
               ;; 모서리/좌표 데이터는 보존
               (cons 'CORNER-BRACE 
                 (if (and (cdr (assoc 'CORNER-BRACE target-data)) (= (car (cdr (assoc 'CORNER-BRACE target-data))) "Y"))
                   (cdr (assoc 'CORNER-BRACE source-data))
                   (cdr (assoc 'CORNER-BRACE target-data))
                 )
               )
               (cons 'UPGRADE-WALE (cdr (assoc 'UPGRADE-WALE target-data)))
               (cons 'V-START (cdr (assoc 'V-START target-data)))
               (cons 'V-END (cdr (assoc 'V-END target-data)))
               (cons 'ANGLE (cdr (assoc 'ANGLE target-data)))
               (cons 'LENGTH (cdr (assoc 'LENGTH target-data)))
             ))
             (setq *segment-list* (update-list-item *segment-list* t-idx new-target))
           )
           (setq paste-mode nil)
           (setq *tsp-data-dirty* T)
           (setq status-msg-text (strcat (itoa (length target-indices)) "개의 세그먼트에 데이터가 한 번에 복사되었습니다!"))
           (if (and *tsp-boundary-ent* *tsp-boundary-orient*) (tsp-redraw-realtime-plan *tsp-boundary-ent* *tsp-boundary-orient*))
         )
         (progn
           (alert "데이터가 텅 비어있는 세그먼트는 원본이 될 수 없습니다.")
           (setq paste-mode nil))
       )
      )
      ((= result 7)
       (setq check-data (nth selected-idx *segment-list*))
       (if (cdr (assoc 'IS-DEFINED check-data))
         (progn
           (tsp-apply-settings-to-all selected-idx)
           (setq status-msg-text "모든 세그먼트에 설정이 일괄 적용되었습니다.")
           (alert (strcat "No." (itoa (1+ selected-idx)) " 설정값이 나머지 전체 목록에 적용되었습니다."))
           (if (and *tsp-boundary-ent* *tsp-boundary-orient*) (tsp-redraw-realtime-plan *tsp-boundary-ent* *tsp-boundary-orient*))
         )
         (alert "복사할 원본이 정의되지 않았습니다.\\n먼저 [입력]을 완료하세요.")
       )
       (setq apply-all-mode nil)
      )
      ((= result 8)
       (setq check-data (nth selected-idx *segment-list*))
       (if (and (cdr (assoc 'SOIL-DATA check-data)) (/= (cdr (assoc 'SOIL-DATA check-data)) '()))
         (progn
           (tsp-apply-soil-to-all selected-idx)
           (setq status-msg-text "모든 세그먼트에 지반 정보가 적용되었습니다.")
           (alert (strcat "No." (itoa (1+ selected-idx)) " 지반 정보가 나머지 전체 목록에 적용되었습니다."))
           (if (and *tsp-boundary-ent* *tsp-boundary-orient*) (tsp-redraw-realtime-plan *tsp-boundary-ent* *tsp-boundary-orient*))
         )
         (alert "복사할 지반 정보가 없습니다.")
       )
       (setq apply-soil-mode nil)
      )
      ((= result 11)
       (setq check-data (nth selected-idx *segment-list*))
       (if (and (cdr (assoc 'SUPPORT-LIST check-data)) (/= (cdr (assoc 'SUPPORT-LIST check-data)) '()))
         (progn
           (tsp-apply-support-to-all selected-idx)
           (setq status-msg-text "모든 세그먼트에 지보재 정보가 적용되었습니다.")
           (alert (strcat "No." (itoa (1+ selected-idx)) " 지보재 정보가 나머지 전체 목록에 적용되었습니다."))
           (if (and *tsp-boundary-ent* *tsp-boundary-orient*) (tsp-redraw-realtime-plan *tsp-boundary-ent* *tsp-boundary-orient*))
         )
         (alert "복사할 지보재 정보가 없습니다.\\n먼저 지보재를 정의해 주세요.")
       )
       (setq apply-support-mode nil)
      )
      ((= result 14)
       (setq check-data (nth selected-idx *segment-list*))
       ;; IS-DEFINED(입력 완료 여부)가 T인지 확실하게 검증
       (if (cdr (assoc 'IS-DEFINED check-data))
         (progn
           (tsp-apply-wall-to-all selected-idx)
           (setq status-msg-text "모든 세그먼트에 흙막이벽 정보가 적용되었습니다.")
           (alert (strcat "No." (itoa (1+ selected-idx)) " 흙막이벽 정보가 나머지 전체 목록에 적용되었습니다."))
           (if (and *tsp-boundary-ent* *tsp-boundary-orient*) (tsp-redraw-realtime-plan *tsp-boundary-ent* *tsp-boundary-orient*))
         )
         (alert "복사할 흙막이벽 정보가 없습니다.\n먼저 원본 세그먼트의 [입력]을 완료해 주세요.")
       )
       (setq apply-wall-mode nil)
      )
      ((= result 15)
       (setq check-data (nth selected-idx *segment-list*))
       ;; IS-DEFINED(입력 완료 여부)가 T인지 확실하게 검증
       (if (cdr (assoc 'IS-DEFINED check-data))
         (progn
           (tsp-apply-brace-to-all selected-idx)
           (setq status-msg-text "조건에 맞는 세그먼트에 사보강재 정보가 적용되었습니다.")
           (alert (strcat "No." (itoa (1+ selected-idx)) " 사보강재 정보가 조건에 맞는 전체 목록에 적용되었습니다."))
           (if (and *tsp-boundary-ent* *tsp-boundary-orient*) (tsp-redraw-realtime-plan *tsp-boundary-ent* *tsp-boundary-orient*))
         )
         (alert "복사할 사보강재 정보가 없습니다.\n먼저 원본 세그먼트의 [입력]을 완료해 주세요.")
       )
       (setq apply-brace-mode nil)
      )
      
      ;; 다중 선택 항목 개별 지우기(초기화) 및 수동 중간말뚝 종속 삭제 연결
      ((= result 9)
       (foreach t-idx selected-indices
         (setq target-id (cdr (assoc 'ID (nth t-idx *segment-list*))))
         (tsp-reset-segment-data t-idx)
         (tsp-delete-manual-post-by-segment target-id)
       )
       (setq status-msg-text (strcat (itoa (length selected-indices)) "개의 설정이 성공적으로 초기화되었습니다."))
       (if (and *tsp-boundary-ent* *tsp-boundary-orient*) (tsp-redraw-realtime-plan *tsp-boundary-ent* *tsp-boundary-orient*))
      )
      ;; 전체 지우기(초기화) 및 모든 수동 중간말뚝 전체 삭제 연결
      ((= result 10)
       (tsp-reset-all-segments)
       (tsp-reset-post-manual) ;; [추가] 전체 수동 중간말뚝 메모리 청소 및 물리적 삭제
       (setq status-msg-text "모든 목록의 설정이 초기화되었습니다.")
       (alert "모든 세그먼트 데이터가 초기 상태로 되돌려졌습니다.")
       (if (and *tsp-boundary-ent* *tsp-boundary-orient*) (tsp-redraw-realtime-plan *tsp-boundary-ent* *tsp-boundary-orient*))
      )
      ((= result 12)
       (if (and *tsp-boundary-ent* *tsp-boundary-orient*) (tsp-redraw-realtime-plan *tsp-boundary-ent* *tsp-boundary-orient*))
      )
      ((= result 13)
       (if tsp-pause-for-measurement
         (tsp-pause-for-measurement)
         (alert "TSP - 도면 제어 모듈이 로드되지 않았습니다.\n(코드가 정상적으로 병합되었는지 확인해주세요.)")
       )
       (setq status-msg-text "도면 확인을 마치고 복귀했습니다. 작업을 계속 진행하세요.")
      )
    )
  )
  result
)

;;;==========================================================================
;;; defun tsp-apply-wall-to-all : 흙막이벽 정보 일괄 적용 로직
;;;==========================================================================
(defun tsp-apply-wall-to-all (source-idx / source-data src-wall-type target-data new-item t-idx updated-list)
  (setq source-data (nth source-idx *segment-list*))
  (setq src-wall-type (if (assoc 'WALL-TYPE source-data) (cdr (assoc 'WALL-TYPE source-data)) "HPILE"))
  (setq updated-list '())
  (setq t-idx 0)
  (foreach target-data *segment-list*
    (if (= t-idx source-idx)
      (setq updated-list (append updated-list (list target-data)))
      (progn
        (setq new-item (list
          (cons 'ID (cdr (assoc 'ID target-data)))
          (cons 'NAME (cdr (assoc 'NAME target-data)))
          (cons 'IS-DEFINED T)
          (cons 'WALL-TYPE src-wall-type)
          (cons 'SECTION-DRAW (cdr (assoc 'SECTION-DRAW target-data)))
          (cons 'SOIL-DATA (cdr (assoc 'SOIL-DATA target-data)))
          (cons 'N-VALUES (cdr (assoc 'N-VALUES target-data)))
          (cons 'HOLE-NO (cdr (assoc 'HOLE-NO target-data)))
          
          ;; 흙막이벽 기본 변수군 (원본 데이터 덮어쓰기)
          (cons 'WALL-SPEC (cdr (assoc 'WALL-SPEC source-data)))
          (cons 'WALL-CUSTOM (cdr (assoc 'WALL-CUSTOM source-data)))
          (cons 'WALE-SPEC (cdr (assoc 'WALE-SPEC source-data)))
          (cons 'WALE-CUSTOM (cdr (assoc 'WALE-CUSTOM source-data)))
          (cons 'CTC (cdr (assoc 'CTC source-data)))
          (cons 'TIMBER-THICKNESS (cdr (assoc 'TIMBER-THICKNESS source-data)))
          (cons 'MAX-DEPTH (cdr (assoc 'MAX-DEPTH source-data)))
          (cons 'EMBED-DEPTH (cdr (assoc 'EMBED-DEPTH source-data)))
          
          ;; CIP 전용 변수군 (원본이 CIP일 때만 복사, 아니면 타겟 데이터 유지)
          (cons 'CIP-MAX-DEPTH (if (= src-wall-type "CIP") (if (assoc 'CIP-MAX-DEPTH source-data) (cdr (assoc 'CIP-MAX-DEPTH source-data)) "10.0") (cdr (assoc 'CIP-MAX-DEPTH target-data))))
          (cons 'CIP-EMBED-DEPTH (if (= src-wall-type "CIP") (if (assoc 'CIP-EMBED-DEPTH source-data) (cdr (assoc 'CIP-EMBED-DEPTH source-data)) "3.0") (cdr (assoc 'CIP-EMBED-DEPTH target-data))))
          (cons 'CIP-HPILE-IDX (if (= src-wall-type "CIP") (if (assoc 'CIP-HPILE-IDX source-data) (cdr (assoc 'CIP-HPILE-IDX source-data)) "2") (cdr (assoc 'CIP-HPILE-IDX target-data))))
          (cons 'CIP-WALE-IDX (if (= src-wall-type "CIP") (if (assoc 'CIP-WALE-IDX source-data) (cdr (assoc 'CIP-WALE-IDX source-data)) "2") (cdr (assoc 'CIP-WALE-IDX target-data))))
          (cons 'CIP-DIA (if (= src-wall-type "CIP") (if (assoc 'CIP-DIA source-data) (cdr (assoc 'CIP-DIA source-data)) "500") (cdr (assoc 'CIP-DIA target-data))))
          (cons 'CIP-MODE-IDX (if (= src-wall-type "CIP") (if (assoc 'CIP-MODE-IDX source-data) (cdr (assoc 'CIP-MODE-IDX source-data)) "0") (cdr (assoc 'CIP-MODE-IDX target-data))))
          (cons 'CIP-OVERLAP (if (= src-wall-type "CIP") (if (assoc 'CIP-OVERLAP source-data) (cdr (assoc 'CIP-OVERLAP source-data)) "0") (cdr (assoc 'CIP-OVERLAP target-data))))
          (cons 'CIP-EQUAL-DIVIDE (if (= src-wall-type "CIP") (if (assoc 'CIP-EQUAL-DIVIDE source-data) (cdr (assoc 'CIP-EQUAL-DIVIDE source-data)) "1") (cdr (assoc 'CIP-EQUAL-DIVIDE target-data))))
          (cons 'CIP-INTERVAL-IDX (if (= src-wall-type "CIP") (if (assoc 'CIP-INTERVAL-IDX source-data) (cdr (assoc 'CIP-INTERVAL-IDX source-data)) "2") (cdr (assoc 'CIP-INTERVAL-IDX target-data))))
          (cons 'CIP-GROUTING-IDX (if (= src-wall-type "CIP") (if (assoc 'CIP-GROUTING-IDX source-data) (cdr (assoc 'CIP-GROUTING-IDX source-data)) "0") (cdr (assoc 'CIP-GROUTING-IDX target-data))))
          
          ;; 나머지 타겟 고유 데이터 유지
          (cons 'WATER-CHK (cdr (assoc 'WATER-CHK target-data)))
          (cons 'WATER-DEPTH (cdr (assoc 'WATER-DEPTH target-data)))
          (cons 'SHOTCRETE-ENABLE (cdr (assoc 'SHOTCRETE-ENABLE target-data)))
          (cons 'SHOTCRETE-CHK (cdr (assoc 'SHOTCRETE-CHK target-data)))
          (cons 'SHOTCRETE-LAYER (cdr (assoc 'SHOTCRETE-LAYER target-data)))
          (cons 'SHOTCRETE-THICK (cdr (assoc 'SHOTCRETE-THICK target-data)))
          (cons 'SUPPORT-LIST (cdr (assoc 'SUPPORT-LIST target-data)))
          (cons 'CORNER-BRACE (cdr (assoc 'CORNER-BRACE target-data)))
          (cons 'UPGRADE-WALE (cdr (assoc 'UPGRADE-WALE target-data)))
          (cons 'V-START (cdr (assoc 'V-START target-data)))
          (cons 'V-END (cdr (assoc 'V-END target-data)))
          (cons 'ANGLE (cdr (assoc 'ANGLE target-data)))
          (cons 'LENGTH (cdr (assoc 'LENGTH target-data)))
        ))
        (setq updated-list (append updated-list (list new-item)))
      )
    )
    (setq t-idx (1+ t-idx))
  )
  (setq *segment-list* updated-list)
  (setq *tsp-data-dirty* T) ; <--- 화면 새로고침 신호 송출
)

;;;==========================================================================
;;; defun tsp-apply-brace-to-all : 사보강재 정보 일괄 적용 로직
;;;==========================================================================
(defun tsp-apply-brace-to-all (source-idx / source-data src-brace target-data new-item t-idx updated-list tgt-brace val)
  (setq source-data (nth source-idx *segment-list*))
  (setq src-brace (cdr (assoc 'CORNER-BRACE source-data)))
  (setq updated-list '())
  (setq t-idx 0)
  (foreach target-data *segment-list*
    (if (= t-idx source-idx)
      (setq updated-list (append updated-list (list target-data)))
      (progn
        (setq tgt-brace (cdr (assoc 'CORNER-BRACE target-data)))
        ;; 타겟이 사보강재가 필요한 곳("Y")일 때만 원본 데이터 복사
        (setq val (if (and tgt-brace (= (car tgt-brace) "Y")) src-brace tgt-brace))
        
        (setq new-item (list
          (cons 'ID (cdr (assoc 'ID target-data)))
          (cons 'NAME (cdr (assoc 'NAME target-data)))
          (cons 'IS-DEFINED T) ; <--- [핵심 수정]
          (cons 'WALL-TYPE (cdr (assoc 'WALL-TYPE target-data)))
          (cons 'SECTION-DRAW (cdr (assoc 'SECTION-DRAW target-data)))
          (cons 'SOIL-DATA (cdr (assoc 'SOIL-DATA target-data)))
          (cons 'N-VALUES (cdr (assoc 'N-VALUES target-data)))
          (cons 'HOLE-NO (cdr (assoc 'HOLE-NO target-data)))
          (cons 'WALL-SPEC (cdr (assoc 'WALL-SPEC target-data)))
          (cons 'WALL-CUSTOM (cdr (assoc 'WALL-CUSTOM target-data)))
          (cons 'WALE-SPEC (cdr (assoc 'WALE-SPEC target-data)))
          (cons 'WALE-CUSTOM (cdr (assoc 'WALE-CUSTOM target-data)))
          (cons 'CTC (cdr (assoc 'CTC target-data)))
          (cons 'TIMBER-THICKNESS (cdr (assoc 'TIMBER-THICKNESS target-data)))
          (cons 'MAX-DEPTH (cdr (assoc 'MAX-DEPTH target-data)))
          (cons 'EMBED-DEPTH (cdr (assoc 'EMBED-DEPTH target-data)))
          (cons 'CIP-MAX-DEPTH (cdr (assoc 'CIP-MAX-DEPTH target-data)))
          (cons 'CIP-EMBED-DEPTH (cdr (assoc 'CIP-EMBED-DEPTH target-data)))
          (cons 'CIP-HPILE-IDX (cdr (assoc 'CIP-HPILE-IDX target-data)))
          (cons 'CIP-WALE-IDX (cdr (assoc 'CIP-WALE-IDX target-data)))
          (cons 'CIP-DIA (cdr (assoc 'CIP-DIA target-data)))
          (cons 'CIP-MODE-IDX (cdr (assoc 'CIP-MODE-IDX target-data)))
          (cons 'CIP-OVERLAP (cdr (assoc 'CIP-OVERLAP target-data)))
          (cons 'CIP-EQUAL-DIVIDE (cdr (assoc 'CIP-EQUAL-DIVIDE target-data)))
          (cons 'CIP-INTERVAL-IDX (cdr (assoc 'CIP-INTERVAL-IDX target-data)))
          (cons 'CIP-GROUTING-IDX (cdr (assoc 'CIP-GROUTING-IDX target-data)))
          (cons 'WATER-CHK (cdr (assoc 'WATER-CHK target-data)))
          (cons 'WATER-DEPTH (cdr (assoc 'WATER-DEPTH target-data)))
          (cons 'SHOTCRETE-ENABLE (cdr (assoc 'SHOTCRETE-ENABLE target-data)))
          (cons 'SHOTCRETE-CHK (cdr (assoc 'SHOTCRETE-CHK target-data)))
          (cons 'SHOTCRETE-LAYER (cdr (assoc 'SHOTCRETE-LAYER target-data)))
          (cons 'SHOTCRETE-THICK (cdr (assoc 'SHOTCRETE-THICK target-data)))
          (cons 'SUPPORT-LIST (cdr (assoc 'SUPPORT-LIST target-data)))
          (cons 'CORNER-BRACE val) ; <--- 조건부 적용
          (cons 'UPGRADE-WALE (cdr (assoc 'UPGRADE-WALE target-data)))
          (cons 'V-START (cdr (assoc 'V-START target-data)))
          (cons 'V-END (cdr (assoc 'V-END target-data)))
          (cons 'ANGLE (cdr (assoc 'ANGLE target-data)))
          (cons 'LENGTH (cdr (assoc 'LENGTH target-data)))
        ))
        (setq updated-list (append updated-list (list new-item)))
      )
    )
    (setq t-idx (1+ t-idx))
  )
  (setq *segment-list* updated-list)
  (setq *tsp-data-dirty* T)
)

;;;;==========================================================================
;;;; defun draw-tsp-legend : 지반 범례(Legend) 도면 작도
;;;;==========================================================================
(defun draw-tsp-legend (pt mode temp-layers / all-data target-data box-w text-w row-h title-h s-factor layer-name item p-name p-pat p-scale p-angle p1 p2 p3 p4 center-pt text-pt final-scale rect-pl num-items num-rows total-w i col row box-x box-y cx cy p-type abbr-name already ad base-y tri-h tri-w-half line1-len line1-start line1-end line1-mid l2-half off-y1 line2-y line2-start line2-end l3-half off-y2 line3-y line3-start line3-end tri-p1 tri-p2 tri-p3 tri-p_top_center tot-p1 tot-p2 tot-p3 tot-p4)
  (setq layer-name "_지반선")
  (setq s-factor (if *tsp-scale-section* (/ *tsp-scale-section* 200.0) 1.0))
  (setq title-h (* 2000.0 s-factor))
  (setq row-h (* 2000.0 s-factor))
  (setq box-w (* 2000.0 s-factor))
  (setq text-w (* 4000.0 s-factor))
  (setq total-w (* 12000.0 s-factor))
  (setq all-data '(
    ("입도양호 자갈(GW)" "GW_" 100.0 0.0)
    ("입도불량 자갈(GP)" "GP_" 100.0 0.0)
    ("실트질 자갈(GM)" "GM_" 100.0 0.0)
    ("점토질 자갈(GC)" "GC_" 100.0 0.0)
    ("입도양호 모래(SW)" "SW_" 100.0 0.0)
    ("입도불량 모래(SP)" "SP_" 100.0 0.0)
    ("실트질 모래(SM)" "SM_" 100.0 0.0)
    ("점토질 모래(SC)" "SC_" 100.0 0.0)
    ("저소성 실트(ML)" "ML_" 100.0 0.0)
    ("고소성 실트(MH)" "MH_" 100.0 0.0)
    ("저소성 점토(CL)" "CL_" 100.0 0.0)
    ("고소성 점토(CH)" "CH_" 100.0 0.0)
    ("전석(BOULDER)" "GRAVEL" 30.0 0.0)
    ("풍화잔류토(RS)" "RS_" 2500.0 0.0)
    ("풍화암(WR)" "WR_" 100.0 0.0)
    ("연암(SR)" "SR_" 100.0 0.0)
    ("경암(HR)" "HR_" 100.0 0.0)
    ("기타" "LINE" 78.74 0.0)
  ))
  (setq target-data '())
  (if (= (strcase mode) "USED")
    (progn
      (foreach layer temp-layers
        (setq p-type (nth 5 layer))
        (setq abbr-name (tsp-get-abbr p-type))
        (setq already nil)
        (foreach td target-data
          (if (= (car td) abbr-name) (setq already t))
        )
        (if (not already)
          (foreach ad all-data
            (if (= (car ad) p-type)
              (setq target-data (append target-data (list (list abbr-name (nth 1 ad) (nth 2 ad) (nth 3 ad)))))
            )
          )
        )
      )
      (if (= *tsp-water-chk* "1")
        (setq target-data (append target-data (list (list "지하수위" "GWL" 1.0 0.0))))
      )
    )
    (progn
      (foreach ad all-data
        ;; "전체" 모드일 때는 "기타" 지층을 범례에서 제외
        (if (/= (nth 0 ad) "기타")
          (setq target-data (append target-data (list (list (tsp-get-abbr (nth 0 ad)) (nth 1 ad) (nth 2 ad) (nth 3 ad)))))
        )
      )
      (setq target-data (append target-data (list (list "지하수위" "GWL" 1.0 0.0))))
    )
  )
  (setq num-items (length target-data))
  (setq num-rows (fix (/ (+ num-items 1) 2)))
  ;; --- 표 외곽선 및 타이틀 작도 ---
  (entmake (list '(0 . "TEXT") '(100 . "AcDbEntity") '(100 . "AcDbText") (cons 8 layer-name) (cons 62 8)
                 (cons 10 (list (+ (car pt) (/ total-w 2.0)) (- (cadr pt) (/ title-h 2.0)) 0.0))
                 (cons 40 (* 800.0 s-factor)) (cons 1 "범   례")
                 (cons 72 1) (cons 73 2) (cons 11 (list (+ (car pt) (/ total-w 2.0)) (- (cadr pt) (/ title-h 2.0)) 0.0))))
  ;; 줌 기능을 위해 전체 범례 외곽 좌표를 독립된 변수에 저장
  (setq tot-p1 (list (car pt) (cadr pt) 0.0))
  (setq tot-p2 (list (+ (car pt) total-w) (cadr pt) 0.0))
  (setq tot-p3 (list (+ (car pt) total-w) (- (cadr pt) (+ title-h (* num-rows row-h))) 0.0))
  (setq tot-p4 (list (car pt) (- (cadr pt) (+ title-h (* num-rows row-h))) 0.0))
  (entmake (list '(0 . "LWPOLYLINE") '(100 . "AcDbEntity") '(100 . "AcDbPolyline") (cons 8 layer-name) (cons 62 8) '(90 . 4) '(70 . 1)
                 (cons 10 tot-p1) (cons 10 tot-p2) (cons 10 tot-p3) (cons 10 tot-p4)))
  (entmake (list '(0 . "LINE") (cons 8 layer-name) (cons 62 8)
                 (cons 10 (list (car pt) (- (cadr pt) title-h) 0.0))
                 (cons 11 (list (+ (car pt) total-w) (- (cadr pt) title-h) 0.0))))
  (foreach vx (list box-w (+ box-w text-w) (+ box-w text-w box-w))
    (entmake (list '(0 . "LINE") (cons 8 layer-name) (cons 62 8)
                   (cons 10 (list (+ (car pt) vx) (- (cadr pt) title-h) 0.0))
                   (cons 11 (list (+ (car pt) vx) (- (cadr pt) (+ title-h (* num-rows row-h))) 0.0))))
  )
  (setq i 1)
  (while (< i num-rows)
    (entmake (list '(0 . "LINE") (cons 8 layer-name) (cons 62 8)
                   (cons 10 (list (car pt) (- (cadr pt) (+ title-h (* i row-h))) 0.0))
                   (cons 11 (list (+ (car pt) total-w) (- (cadr pt) (+ title-h (* i row-h))) 0.0))))
    (setq i (1+ i))
  )
  ;; --- 데이터 및 해치/기호 채우기 ---
  (setq i 0)
  (while (< i num-items)
    (setq item (nth i target-data))
    (setq p-name (nth 0 item) p-pat (nth 1 item) p-scale (nth 2 item) p-angle (nth 3 item))
    (setq col (/ i num-rows))
    (setq row (rem i num-rows))
    (setq box-x (+ (car pt) (* col (+ box-w text-w))))
    (setq box-y (- (cadr pt) (+ title-h (* row row-h))))
    ;; 여기서 내부 해치 박스 그리느라 p1, p2, p3, p4가 오염됨
    (setq p1 (list box-x box-y 0.0))
    (setq p2 (list (+ box-x box-w) box-y 0.0))
    (setq p3 (list (+ box-x box-w) (- box-y row-h) 0.0))
    (setq p4 (list box-x (- box-y row-h) 0.0))
    (setq center-pt (list (+ box-x (/ box-w 2.0)) (- box-y (/ row-h 2.0)) 0.0))
    (if (= p-pat "GWL")
      (progn
        (setq cx (car center-pt) cy (cadr center-pt))
        (setq base-y (- cy (* 300.0 s-factor)))
        (setq tri-h (* 800.0 s-factor))
        (setq tri-w-half (/ tri-h (sqrt 3.0)))
        (setq line1-len (* 2000.0 s-factor))
        (setq line1-start (list (- cx (/ line1-len 2.0)) base-y 0.0))
        (setq line1-end (list (+ cx (/ line1-len 2.0)) base-y 0.0))
        (setq line1-mid (list cx base-y 0.0))
        (entmake (list '(0 . "LWPOLYLINE") '(100 . "AcDbEntity") '(100 . "AcDbPolyline") (cons 8 layer-name) (cons 62 8) '(90 . 2) '(70 . 0) (cons 10 line1-start) (cons 10 line1-end)))
        (setq l2-half (* 750.0 s-factor)) (setq off-y1 (* 100.0 s-factor)) (setq line2-y (- base-y off-y1))
        (setq line2-start (list (- cx l2-half) line2-y 0.0)) (setq line2-end (list (+ cx l2-half) line2-y 0.0))
        (entmake (list '(0 . "LWPOLYLINE") '(100 . "AcDbEntity") '(100 . "AcDbPolyline") (cons 8 layer-name) (cons 62 8) '(90 . 2) '(70 . 0) (cons 10 line2-start) (cons 10 line2-end)))
        (setq l3-half (* 500.0 s-factor)) (setq off-y2 (* 200.0 s-factor)) (setq line3-y (- base-y off-y2))
        (setq line3-start (list (- cx l3-half) line3-y 0.0)) (setq line3-end (list (+ cx l3-half) line3-y 0.0))
        (entmake (list '(0 . "LWPOLYLINE") '(100 . "AcDbEntity") '(100 . "AcDbPolyline") (cons 8 layer-name) (cons 62 8) '(90 . 2) '(70 . 0) (cons 10 line3-start) (cons 10 line3-end)))
        (setq tri-p3 line1-mid)
        (setq tri-p1 (list (- cx tri-w-half) (+ base-y tri-h) 0.0))
        (setq tri-p2 (list (+ cx tri-w-half) (+ base-y tri-h) 0.0))
        (entmake (list '(0 . "LWPOLYLINE") '(100 . "AcDbEntity") '(100 . "AcDbPolyline") (cons 8 layer-name) (cons 62 8) '(90 . 3) '(70 . 1) (cons 10 tri-p1) (cons 10 tri-p2) (cons 10 tri-p3)))
        (setq tri-p_top_center (list cx (+ base-y tri-h) 0.0))
        (entmake (list '(0 . "SOLID") '(100 . "AcDbEntity") '(100 . "AcDbTrace") (cons 8 layer-name) (cons 62 8) (cons 10 tri-p1) (cons 11 tri-p_top_center) (cons 12 tri-p3) (cons 13 tri-p3)))
      )
      (progn
        (entmake (list '(0 . "LWPOLYLINE") '(100 . "AcDbEntity") '(100 . "AcDbPolyline") (cons 8 layer-name) (cons 62 8) '(90 . 4) '(70 . 1)
                       (cons 10 p1) (cons 10 p2) (cons 10 p3) (cons 10 p4)))
        (setq rect-pl (entlast))
        (setq final-scale (* p-scale s-factor 2.0))
        (if rect-pl
          (tsp-apply-custom-hatch rect-pl p-pat final-scale (* p-angle (/ pi 180.0)) layer-name 8 center-pt)
        )
      )
    )
    (setq text-pt (list (+ box-x box-w (/ text-w 2.0)) (- box-y (/ row-h 2.0)) 0.0))
    (entmake (list '(0 . "TEXT") '(100 . "AcDbEntity") '(100 . "AcDbText") (cons 8 layer-name) (cons 62 8)
                   (cons 10 text-pt) (cons 40 (* 600.0 s-factor)) (cons 1 p-name)
                   (cons 72 1) (cons 73 2) (cons 11 text-pt)))
    (setq i (1+ i))
  )
  (princ "\n범례 생성 완료.")
  (list tot-p1 tot-p2 tot-p3 tot-p4)
)


;;; --------------------------------------------------------------------------
;;; Function: tsp-get-abbr, tsp-format-soil-name
;;; Description: 지층명칭 추출 및 변환
;;; --------------------------------------------------------------------------
(defun tsp-get-abbr (str / p1 p2 res)
  (setq p1 (vl-string-search "(" str))
  (setq p2 (vl-string-search ")" str))
  (if (and p1 p2 (> p2 p1))
    (setq res (substr str (+ p1 2) (- p2 p1 1)))
    (setq res str)
  )
  (if (= res "BOULDER") (setq res "BO"))
  res
)

(defun tsp-format-soil-name (str / p1 base-str)
  (setq p1 (vl-string-search "(" str))
  (if p1
    (setq base-str (substr str 1 p1))
    (setq base-str str)
  )
  (while (and (> (strlen base-str) 0) (= (substr base-str (strlen base-str) 1) " "))
    (setq base-str (substr base-str 1 (1- (strlen base-str))))
  )
  (while (vl-string-search "저소성" base-str)
    (setq base-str (vl-string-subst "압축성 낮은" "저소성" base-str))
  )
  (while (vl-string-search "고소성" base-str)
    (setq base-str (vl-string-subst "압축성 높은" "고소성" base-str))
  )
  base-str
)


;;;;==========================================================================
;;;; defun soil-dialog-callback : 지반 정보 입력 메인 대화상자 콜백
;;;;==========================================================================
(defun soil-dialog-callback (dcl-path / dcl-id result soil-data-list temp-layers temp-n-vals temp-hole soil-labels h-val phi-val r-idx sel-idx sel-item sel-name sel-depth sel-type-name sel-phi type-idx i user-name soil-depth-str soil-phi-str soil-depth soil-phi last-depth h-pattern h-scale h-angle new-layer new-list selected-type-info lg-mode pt leg-box n-hit n-pen n-depth-str n-depth n-str new-n-val new-n-list n-sel-idx n-sel-item slash-pos current-rock-list extracted-n-vals)
  (setq dcl-id (load_dialog dcl-path))
  (setq temp-layers (if *tsp-soil-layers* *tsp-soil-layers* '()))
  (setq temp-n-vals (if *tsp-n-values* *tsp-n-values* '()))
  (setq temp-hole (if *tsp-hole-no* *tsp-hole-no* "BH-"))
  (setq soil-data-list '(
    ("입도양호 자갈(GW)" "GW_" 100.0 0.0) ("입도불량 자갈(GP)" "GP_" 100.0 0.0)
    ("실트질 자갈(GM)" "GM_" 100.0 0.0) ("점토질 자갈(GC)" "GC_" 100.0 0.0)
    ("입도양호 모래(SW)" "SW_" 100.0 0.0) ("입도불량 모래(SP)" "SP_" 100.0 0.0)
    ("실트질 모래(SM)" "SM_" 100.0 0.0) ("점토질 모래(SC)" "SC_" 100.0 0.0)
    ("저소성 실트(ML)" "ML_" 100.0 0.0) ("고소성 실트(MH)" "MH_" 100.0 0.0)
    ("저소성 점토(CL)" "CL_" 100.0 0.0) ("고소성 점토(CH)" "CH_" 100.0 0.0)
    ("전석(BOULDER)" "GRAVEL" 30.0 0.0) ("풍화잔류토(RS)" "RS_" 2500.0 0.0)
    ("풍화암(WR)" "WR_" 100.0 0.0) ("연암(SR)" "SR_" 100.0 0.0)
    ("경암(HR)" "HR_" 100.0 0.0) ("기타" "LINE" 78.74 0.0)
  ))
  (setq soil-labels (mapcar 'car soil-data-list))
  (setq loop-dcl t)
  (setq result 0)
  (while loop-dcl
    (setq dcl-id (load_dialog dcl-path))
    (if (new_dialog "tsp_soil" dcl-id)
      (progn
        (start_list "soil_type") (mapcar 'add_list soil-labels) (end_list) (set_tile "soil_type" "0")

        ;; [팝업 리스트 업데이트]
        (defun update-rock-popup (/ rock-list l-name l-type)
          (setq rock-list '())
          (foreach layer temp-layers
            (setq l-name (car layer) l-type (nth 5 layer))
            (if (or (and l-type (or (wcmatch l-type "*풍화암*") (wcmatch l-type "*연암*") (wcmatch l-type "*경암*")))
                    (wcmatch l-name "*풍화암*") (wcmatch l-name "*연암*") (wcmatch l-name "*경암*"))
              (setq rock-list (append rock-list (list l-name)))
            )
          )
          (if (> (length rock-list) 0)
            (progn 
              (start_list "soil_shotcrete_layer") (mapcar 'add_list rock-list) (end_list)
              (start_list "soil_cip_rock_layer") (mapcar 'add_list rock-list) (end_list)
            )
            (progn 
              (start_list "soil_shotcrete_layer") (add_list "암반층 없음") (end_list)
              (start_list "soil_cip_rock_layer") (add_list "암반층 없음") (end_list)
            )
          )
          rock-list
        )

        ;; [숏크리트 UI 활성/비활성 제어]
        (defun toggle-shotcrete-ui (is-master-on has-rock)
          (if has-rock
            (progn
              (mode_tile "soil_shotcrete_enable" 0)
              (if is-master-on
                (progn
                  (mode_tile "soil_shotcrete_thick" 0)
                  (mode_tile "soil_shotcrete_chk" 0)
                  (if (= (get_tile "soil_shotcrete_chk") "1") 
                    (mode_tile "soil_shotcrete_layer" 0) 
                    (mode_tile "soil_shotcrete_layer" 1))
                )
                (progn
                  (mode_tile "soil_shotcrete_thick" 1)
                  (mode_tile "soil_shotcrete_chk" 1)
                  (mode_tile "soil_shotcrete_layer" 1)
                )
              )
            )
            (progn
              (set_tile "soil_shotcrete_enable" "0")
              (setq *tsp-shotcrete-enable* "0")
              (mode_tile "soil_shotcrete_enable" 1)
              (mode_tile "soil_shotcrete_thick" 1)
              (mode_tile "soil_shotcrete_chk" 1)
              (mode_tile "soil_shotcrete_layer" 1)
            )
          )
        )

        ;; [CIP 암반 정착 UI 활성/비활성 제어 - 신규 체크박스 연동]
        (defun toggle-cip-rock-ui (is-cip-mode has-rock)
          (if (and is-cip-mode has-rock)
            (progn
              (mode_tile "soil_rock_embed_chk" 0)
              ;; 암반 정착을 체크해야만 정착고 입력칸 활성화
              (if (= (get_tile "soil_rock_embed_chk") "1")
                (mode_tile "soil_rock_embed" 0)
                (mode_tile "soil_rock_embed" 1)
              )
              (mode_tile "soil_cip_rock_chk" 0)
              ;; 암반지정 체크해야만 팝업 리스트 활성화
              (if (= (get_tile "soil_cip_rock_chk") "1")
                (mode_tile "soil_cip_rock_layer" 0)
                (mode_tile "soil_cip_rock_layer" 1)
              )
            )
            (progn
              (mode_tile "soil_rock_embed_chk" 1)
              (mode_tile "soil_rock_embed" 1)
              (mode_tile "soil_cip_rock_chk" 1)
              (mode_tile "soil_cip_rock_layer" 1)
            )
          )
        )

        ;; [리스트 업데이트 및 연쇄 호출]
        (defun update-soil-list ()
          (start_list "soil_list")
          (foreach layer temp-layers
            (setq phi-val (if (nth 6 layer) (rtos (nth 6 layer) 2 1) "0.0"))
            (add_list (strcat (car layer) " - " (nth 5 layer) " - " (rtos (cadr layer) 2 2) "m - " phi-val "도")))
          (end_list)
          (setq current-rock-list (update-rock-popup))
          (toggle-shotcrete-ui (= (get_tile "soil_shotcrete_enable") "1") (> (length current-rock-list) 0))
          (toggle-cip-rock-ui (= *tsp-wall-type* "CIP") (> (length current-rock-list) 0))
        )

        (defun update-n-val-list ()
          (start_list "n_val_list")
          (foreach n-item temp-n-vals
            (add_list (strcat (cadr n-item) " - " (rtos (car n-item) 2 2) "m"))
          )
          (end_list)
        )

        ;; [N치 동작 관련 함수 생략 (내용은 그대로 유지됨)]
        (defun action-n-add (/ hit pen dep-str dep nstr nval)
          (setq hit (vl-string-trim " " (get_tile "n_hit")))
          (setq pen (vl-string-trim " " (get_tile "n_pen")))
          (setq dep-str (vl-string-trim " " (get_tile "n_depth")))
          (if (and dep-str (/= dep-str "") (numberp (read dep-str)))
            (progn (setq dep (atof dep-str)) (if (and (= hit "") (= pen "")) (alert "타격수/관입량 입력요망!") (progn (if (and (= hit "") (/= pen "")) (setq hit "50")) (if (and (/= hit "") (= pen "")) (setq pen "30")) (setq nstr (strcat hit "/" pen)) (setq nval (list dep nstr)) (setq temp-n-vals (append temp-n-vals (list nval))) (setq temp-n-vals (vl-sort temp-n-vals '(lambda (a b) (< (car a) (car b))))) (update-n-val-list) (set_tile "n_hit" "") (set_tile "n_pen" "") (set_tile "n_depth" "")))) (alert "깊이 오류!"))
        )
        (defun action-n-modify (/ n-sel-idx-str n-sel-idx hit pen dep-str dep nstr nval new-n-list i)
          (setq n-sel-idx-str (get_tile "n_val_list"))
          (if (and n-sel-idx-str (/= n-sel-idx-str ""))
            (progn (setq n-sel-idx (atoi n-sel-idx-str)) (setq hit (vl-string-trim " " (get_tile "n_hit"))) (setq pen (vl-string-trim " " (get_tile "n_pen"))) (setq dep-str (vl-string-trim " " (get_tile "n_depth"))) (if (and dep-str (/= dep-str "") (numberp (read dep-str))) (progn (setq dep (atof dep-str)) (if (and (= hit "") (= pen "")) (alert "타격수/관입량 입력요망!") (progn (if (and (= hit "") (/= pen "")) (setq hit "50")) (if (and (/= hit "") (= pen "")) (setq pen "30")) (setq nstr (strcat hit "/" pen)) (setq nval (list dep nstr)) (setq new-n-list '()) (setq i 0) (foreach item temp-n-vals (if (/= i n-sel-idx) (setq new-n-list (append new-n-list (list item)))) (setq i (1+ i))) (setq new-n-list (append new-n-list (list nval))) (setq temp-n-vals (vl-sort new-n-list '(lambda (a b) (< (car a) (car b))))) (update-n-val-list) (set_tile "n_hit" "") (set_tile "n_pen" "") (set_tile "n_depth" "")))) (alert "깊이 오류!"))) (alert "선택 오류!")
          )
        )
        (defun action-n-delete (/ n-sel-idx-str n-sel-idx new-n-list i)
          (setq n-sel-idx-str (get_tile "n_val_list"))
          (if (and n-sel-idx-str (/= n-sel-idx-str ""))
            (progn (setq n-sel-idx (atoi n-sel-idx-str)) (setq new-n-list '()) (setq i 0) (foreach item temp-n-vals (if (/= i n-sel-idx) (setq new-n-list (append new-n-list (list item)))) (setq i (1+ i))) (setq temp-n-vals new-n-list) (update-n-val-list) (set_tile "n_hit" "") (set_tile "n_pen" "") (set_tile "n_depth" "")) (alert "선택 오류!")
          )
        )
        (defun action-n-select (/ n-sel-idx n-sel-item n-str n-depth slash-pos)
          (setq n-sel-idx (atoi (get_tile "n_val_list")))
          (if (and temp-n-vals (>= n-sel-idx 0) (< n-sel-idx (length temp-n-vals)))
            (progn (setq n-sel-item (nth n-sel-idx temp-n-vals)) (setq n-str (cadr n-sel-item)) (setq n-depth (car n-sel-item)) (set_tile "n_depth" (rtos n-depth 2 2)) (setq slash-pos (vl-string-search "/" n-str)) (if slash-pos (progn (set_tile "n_hit" (substr n-str 1 slash-pos)) (set_tile "n_pen" (substr n-str (+ slash-pos 2)))) (progn (set_tile "n_hit" n-str) (set_tile "n_pen" ""))))
          )
        )

        ;; ---------------- UI 초기값 세팅 ----------------
        (set_tile "hole_no" temp-hole)        (update-n-val-list)
        (set_tile "soil_max_depth" (rtos *tsp-max-depth* 2 2))
        (set_tile "soil_embed_depth" (rtos *tsp-embed-depth* 2 2))
        
        ;; [신규] CIP 암반 정착 초기값 세팅
        (set_tile "soil_rock_embed_chk" (if *tsp-rock-embed-chk* *tsp-rock-embed-chk* "1"))
        (set_tile "soil_rock_embed" *tsp-rock-embed*)
        (set_tile "soil_cip_rock_chk" (if *tsp-cip-rock-chk* *tsp-cip-rock-chk* "0"))
        
        (set_tile "soil_shotcrete_enable" (if *tsp-shotcrete-enable* *tsp-shotcrete-enable* "1"))
        (if (or (null *tsp-shotcrete-thick*) (= *tsp-shotcrete-thick* 0.0))
          (progn
            (if (= *tsp-hpile-spec* "User-defined")
              (setq h-val (float (car *tsp-hpile-custom*)))
              (setq h-val (float (car (parse-h-spec *tsp-hpile-spec*))))
            )
            (setq *tsp-shotcrete-thick* (/ h-val 2.0))
          )
        )
        (set_tile "soil_shotcrete_thick" (rtos *tsp-shotcrete-thick* 2 0))
        (set_tile "soil_shotcrete_chk" (if *tsp-shotcrete-chk* *tsp-shotcrete-chk* "0"))
        
        (set_tile "soil_water_chk" (if *tsp-water-chk* *tsp-water-chk* "0"))
        (if (= (get_tile "soil_water_chk") "1") (progn (mode_tile "soil_water_depth" 0) (set_tile "soil_water_depth" (rtos *tsp-water-depth* 2 2))) (mode_tile "soil_water_depth" 1))
        
        (update-soil-list)
        
        (if (and *tsp-shotcrete-layer* (/= *tsp-shotcrete-layer* "") current-rock-list)
          (if (setq r-idx (vl-position *tsp-shotcrete-layer* current-rock-list))
            (set_tile "soil_shotcrete_layer" (itoa r-idx))
          )
        )
        (if (and *tsp-cip-rock-layer* (/= *tsp-cip-rock-layer* "") current-rock-list)
          (if (setq r-idx (vl-position *tsp-cip-rock-layer* current-rock-list))
            (set_tile "soil_cip_rock_layer" (itoa r-idx))
          )
        )

        ;; ---------------- 이벤트 (액션 타일) ----------------
        (action_tile "soil_water_chk" "(if (= $value \"1\") (mode_tile \"soil_water_depth\" 0) (mode_tile \"soil_water_depth\" 1))")
        (action_tile "soil_shotcrete_enable" "(progn (setq *tsp-shotcrete-enable* $value) (toggle-shotcrete-ui (= $value \"1\") (> (length current-rock-list) 0)))")
        (action_tile "soil_shotcrete_thick" "(setq *tsp-shotcrete-thick* (atof $value))")
        (action_tile "soil_shotcrete_chk" "(if (= $value \"1\") (mode_tile \"soil_shotcrete_layer\" 0) (mode_tile \"soil_shotcrete_layer\" 1))")
        
        ;; CIP 정착 체크박스 클릭 시 드롭다운 활성화 액션
        (action_tile "soil_cip_rock_chk" "(progn (setq *tsp-cip-rock-chk* $value) (if (= $value \"1\") (mode_tile \"soil_cip_rock_layer\" 0) (mode_tile \"soil_cip_rock_layer\" 1)))")
        
        ;; [신규] 암반 정착 사용 여부 토글 액션
        (action_tile "soil_rock_embed_chk" "(progn (setq *tsp-rock-embed-chk* $value) (if (= $value \"1\") (mode_tile \"soil_rock_embed\" 0) (mode_tile \"soil_rock_embed\" 1)))")
        
        (action_tile "soil_list" "(progn (setq sel-idx (atoi $value)) (if (and temp-layers (>= sel-idx 0) (< sel-idx (length temp-layers))) (progn (setq sel-item (nth sel-idx temp-layers)) (setq sel-name (car sel-item)) (setq sel-depth (cadr sel-item)) (setq sel-type-name (nth 5 sel-item)) (setq sel-phi (nth 6 sel-item)) (set_tile \"soil_user_name\" sel-name) (set_tile \"soil_depth\" (rtos sel-depth 2 2)) (if sel-phi (set_tile \"soil_phi\" (rtos sel-phi 2 1)) (set_tile \"soil_phi\" \"\")) (setq type-idx 0) (setq i 0) (foreach item soil-data-list (if (= (car item) sel-type-name) (setq type-idx i)) (setq i (1+ i))) (set_tile \"soil_type\" (itoa type-idx)))))")
        (action_tile "btn_add" "(progn (setq type-idx (atoi (get_tile \"soil_type\"))) (setq selected-type-info (nth type-idx soil-data-list)) (setq type-name (car selected-type-info)) (setq user-name (get_tile \"soil_user_name\")) (if (or (not user-name) (= user-name \"\")) (setq user-name (tsp-format-soil-name type-name))) (setq soil-depth-str (get_tile \"soil_depth\")) (setq soil-phi-str (get_tile \"soil_phi\")) (if (and soil-depth-str (/= soil-depth-str \"\") (numberp (read soil-depth-str))) (progn (setq soil-depth (atof soil-depth-str)) (setq soil-phi (if (numberp (read soil-phi-str)) (atof soil-phi-str) 0.0)) (setq last-depth (if temp-layers (cadr (last temp-layers)) 0.0)) (if (> soil-depth last-depth) (progn (setq h-pattern (nth 1 selected-type-info)) (setq h-scale (nth 2 selected-type-info)) (setq h-angle (nth 3 selected-type-info)) (setq new-layer (list user-name soil-depth h-pattern h-scale h-angle type-name soil-phi)) (setq temp-layers (append temp-layers (list new-layer))) (update-soil-list) (set_tile \"soil_user_name\" \"\") (set_tile \"soil_depth\" \"\") (set_tile \"soil_phi\" \"\") (mode_tile \"soil_user_name\" 2)) (alert \"깊이는 이전 지층보다 깊어야 합니다!\"))) (alert \"깊이를 올바르게 입력하세요!\")))")
        (action_tile "btn_modify" "(progn (setq sel-idx-str (get_tile \"soil_list\")) (if (and sel-idx-str (/= sel-idx-str \"\")) (progn (setq sel-idx (atoi sel-idx-str)) (setq type-idx (atoi (get_tile \"soil_type\"))) (setq selected-type-info (nth type-idx soil-data-list)) (setq type-name (car selected-type-info)) (setq user-name (get_tile \"soil_user_name\")) (if (or (not user-name) (= user-name \"\")) (setq user-name (tsp-format-soil-name type-name))) (setq soil-depth-str (get_tile \"soil_depth\")) (setq soil-phi-str (get_tile \"soil_phi\")) (if (and soil-depth-str (/= soil-depth-str \"\") (numberp (read soil-depth-str))) (progn (setq soil-depth (atof soil-depth-str)) (setq soil-phi (if (numberp (read soil-phi-str)) (atof soil-phi-str) 0.0)) (setq h-pattern (nth 1 selected-type-info)) (setq h-scale (nth 2 selected-type-info)) (setq h-angle (nth 3 selected-type-info)) (setq new-layer (list user-name soil-depth h-pattern h-scale h-angle type-name soil-phi)) (setq i 0) (setq new-list '()) (foreach item temp-layers (if (= i sel-idx) (setq new-list (append new-list (list new-layer))) (setq new-list (append new-list (list item)))) (setq i (1+ i))) (setq temp-layers new-list) (update-soil-list) (set_tile \"soil_list\" (itoa sel-idx))) (alert \"수정할 깊이를 올바르게 입력하세요!\"))) (alert \"수정할 항목을 목록에서 선택하세요!\")))")
        (action_tile "btn_delete" "(progn (setq sel-idx (atoi (get_tile \"soil_list\"))) (if (and temp-layers (>= sel-idx 0) (< sel-idx (length temp-layers))) (progn (setq temp-layers (vl-remove (nth sel-idx temp-layers) temp-layers)) (update-soil-list)) (alert \"삭제할 항목을 선택하세요!\")))")
        (action_tile "btn_clear" "(progn (setq temp-layers '()) (update-soil-list))")
        (action_tile "btn_n_add" "(action-n-add)")
        (action_tile "btn_n_modify" "(action-n-modify)")
        (action_tile "btn_n_delete" "(action-n-delete)")
        (action_tile "btn_n_clear" "(progn (setq temp-n-vals '()) (update-n-val-list) (set_tile \"n_hit\" \"\") (set_tile \"n_pen\" \"\") (set_tile \"n_depth\" \"\"))")
        (action_tile "btn_n_get_dwg" "(progn (setq temp-hole (get_tile \"hole_no\")) (setq *tsp-water-chk* (get_tile \"soil_water_chk\")) (if (= *tsp-water-chk* \"1\") (setq *tsp-water-depth* (atof (get_tile \"soil_water_depth\"))) (setq *tsp-water-depth* 0.0)) (setq *tsp-shotcrete-chk* (get_tile \"soil_shotcrete_chk\")) (if (and (= *tsp-shotcrete-chk* \"1\") current-rock-list (> (length current-rock-list) 0)) (setq *tsp-shotcrete-layer* (nth (atoi (get_tile \"soil_shotcrete_layer\")) current-rock-list))) (done_dialog 4))")
        (action_tile "n_val_list" "(action-n-select)")
        (action_tile "btn_legend" "(progn (setq temp-hole (get_tile \"hole_no\")) (setq *tsp-water-chk* (get_tile \"soil_water_chk\")) (if (= *tsp-water-chk* \"1\") (setq *tsp-water-depth* (atof (get_tile \"soil_water_depth\"))) (setq *tsp-water-depth* 0.0)) (setq *tsp-shotcrete-chk* (get_tile \"soil_shotcrete_chk\")) (if (and (= *tsp-shotcrete-chk* \"1\") current-rock-list (> (length current-rock-list) 0)) (setq *tsp-shotcrete-layer* (nth (atoi (get_tile \"soil_shotcrete_layer\")) current-rock-list))) (done_dialog 3))")
        (action_tile "btn_measure" "(progn (setq temp-hole (get_tile \"hole_no\")) (setq *tsp-water-chk* (get_tile \"soil_water_chk\")) (if (= *tsp-water-chk* \"1\") (setq *tsp-water-depth* (atof (get_tile \"soil_water_depth\"))) (setq *tsp-water-depth* 0.0)) (setq *tsp-shotcrete-chk* (get_tile \"soil_shotcrete_chk\")) (if (and (= *tsp-shotcrete-chk* \"1\") current-rock-list (> (length current-rock-list) 0)) (setq *tsp-shotcrete-layer* (nth (atoi (get_tile \"soil_shotcrete_layer\")) current-rock-list))) (done_dialog 5))")
        
        ;; [중요] 확인 버튼을 눌렀을 때 체크가 꺼져있으면 정착고 값을 "0"으로 강제 덮어쓰기
        (action_tile "accept" "(progn
          (setq *tsp-max-depth* (atof (get_tile \"soil_max_depth\")))
          (setq *tsp-embed-depth* (atof (get_tile \"soil_embed_depth\")))
          
          (setq *tsp-rock-embed-chk* (get_tile \"soil_rock_embed_chk\"))
          (if (= *tsp-rock-embed-chk* \"1\")
            (setq *tsp-rock-embed* (get_tile \"soil_rock_embed\"))
            (setq *tsp-rock-embed* \"0\") ;; 체크가 해제되어 있다면 무조건 0 저장
          )
          
          (setq *tsp-cip-rock-chk* (get_tile \"soil_cip_rock_chk\"))
          (setq *tsp-soil-layers* temp-layers)
          (setq *tsp-n-values* temp-n-vals)
          (setq *tsp-hole-no* (get_tile \"hole_no\"))
          (setq *tsp-water-chk* (get_tile \"soil_water_chk\"))
          (if (= *tsp-water-chk* \"1\") (setq *tsp-water-depth* (atof (get_tile \"soil_water_depth\"))) (setq *tsp-water-depth* 0.0))
          (setq *tsp-shotcrete-enable* (get_tile \"soil_shotcrete_enable\"))
          (setq *tsp-shotcrete-chk* (get_tile \"soil_shotcrete_chk\"))
          (setq *tsp-shotcrete-thick* (atof (get_tile \"soil_shotcrete_thick\")))
          
          (if (and (= *tsp-shotcrete-chk* \"1\") current-rock-list (> (length current-rock-list) 0))
            (setq *tsp-shotcrete-layer* (nth (atoi (get_tile \"soil_shotcrete_layer\")) current-rock-list))
            (setq *tsp-shotcrete-layer* \"\")
          )
          (if (and (= *tsp-cip-rock-chk* \"1\") current-rock-list (> (length current-rock-list) 0))
            (setq *tsp-cip-rock-layer* (nth (atoi (get_tile \"soil_cip_rock_layer\")) current-rock-list))
            (setq *tsp-cip-rock-layer* \"\")
          )
          (done_dialog 1))")
        
        (action_tile "back" "(done_dialog 2)")
        (action_tile "cancel" "(done_dialog 0)")
        (setq result (start_dialog))
        (unload_dialog dcl-id)
        
        ;; (결과 처리 cond 부분 생략 없이 유지)
        (cond
          ((= result 3)
           (setq lg-mode nil pt nil)
           (if (null temp-layers)
             (setq lg-mode "All")
             (progn
               (initget "All Used")
               (setq lg-mode (vl-catch-all-apply 'getkword (list "\n범례 출력 방식을 선택하세요 [전체(A)/사용된지층(U)] <All>: ")))
               (if (vl-catch-all-error-p lg-mode) (setq lg-mode nil) (if (null lg-mode) (setq lg-mode "All")))
             )
           )
           (if lg-mode
             (progn
               (setq pt (vl-catch-all-apply 'getpoint (list "\n범례를 삽입할 기준점(좌측상단)을 클릭하세요: ")))
               (if (vl-catch-all-error-p pt) (setq pt nil))
             )
           )
           (if (and lg-mode pt)
             (progn (setq leg-box (draw-tsp-legend pt lg-mode temp-layers)) (if leg-box (tsp-zoom-legend leg-box)))
             (princ "\n범례 생성이 취소되었습니다. 지반 정의 창으로 되돌아갑니다.")
           )
          )
          ((= result 4)
           (setq extracted-n-vals (tsp-get-nvalue-from-drawing))
           (if extracted-n-vals
             (progn
               (setq temp-n-vals (append temp-n-vals extracted-n-vals))
               (setq temp-n-vals (vl-sort temp-n-vals '(lambda (a b) (< (car a) (car b)))))
             )
           )
          )
          ((= result 5)
           (if tsp-pause-for-measurement
             (tsp-pause-for-measurement)
             (alert "TSP - 도면 제어 모듈이 로드되지 않았습니다.")
           )
          )
          (t (setq loop-dcl nil))
        )
      )
      (setq loop-dcl nil)
    )
  )
  result
)


;;;;==========================================================================
;;;; defun hpile-dialog-callback : H-Pile 규격 설정 대화상자 콜백
;;;;==========================================================================
(defun hpile-dialog-callback (dcl-path / dcl-id result idx std-len val-h val-b val-tw val-tf)
  (setq dcl-id (load_dialog dcl-path))
  (if (new_dialog "tsp_hpile" dcl-id)
    (progn
      ;; 1. 규격 목록 정의 (전역 변수 사용 + User-defined 자동 추가)
      (start_list "hpile_spec")
      (mapcar 'add_list (append *tsp-std-wall-list* '("User-defined")))
      (end_list)
      (start_list "wale_spec")
      (mapcar 'add_list (append *tsp-std-wall-list* '("User-defined")))
      (end_list)
      ;; 표준 리스트 길이 (User-defined 판별용)
      (setq std-len (length *tsp-std-wall-list*))
      ;; 2. 초기값 설정 로직 (리스트에서 현재 값의 위치를 찾음)
      ;; [H-Pile 설정]
      (if (setq idx (vl-position *tsp-hpile-spec* *tsp-std-wall-list*))
        (set_tile "hpile_spec" (itoa idx))      ; 리스트에 있으면 해당 인덱스 선택
        (set_tile "hpile_spec" (itoa std-len))  ; 없으면 마지막(User-defined) 선택
      )
      ;; 사용자 정의 입력창 활성/비활성 상태 동기화
      (if (= (get_tile "hpile_spec") (itoa std-len))
        (progn
           (if *tsp-hpile-custom*
             (progn
               (set_tile "hpile_h" (itoa (nth 0 *tsp-hpile-custom*)))
               (set_tile "hpile_b" (itoa (nth 1 *tsp-hpile-custom*)))
               (set_tile "hpile_tw" (itoa (nth 2 *tsp-hpile-custom*)))
               (set_tile "hpile_tf" (itoa (nth 3 *tsp-hpile-custom*)))
             )
           )
           (mode_tile "hpile_h" 0) (mode_tile "hpile_b" 0) (mode_tile "hpile_tw" 0) (mode_tile "hpile_tf" 0)
        )
        (progn (mode_tile "hpile_h" 1) (mode_tile "hpile_b" 1) (mode_tile "hpile_tw" 1) (mode_tile "hpile_tf" 1))
      )
      ;; [Wale 설정]
      (if (setq idx (vl-position *tsp-wale-spec* *tsp-std-wall-list*))
        (set_tile "wale_spec" (itoa idx))
        (set_tile "wale_spec" (itoa std-len))
      )
      (if (= (get_tile "wale_spec") (itoa std-len))
        (progn
           (if *tsp-wale-custom*
             (progn
               (set_tile "wale_h" (itoa (nth 0 *tsp-wale-custom*)))
               (set_tile "wale_b" (itoa (nth 1 *tsp-wale-custom*)))
               (set_tile "wale_tw" (itoa (nth 2 *tsp-wale-custom*)))
               (set_tile "wale_tf" (itoa (nth 3 *tsp-wale-custom*)))
             )
           )
           (mode_tile "wale_h" 0) (mode_tile "wale_b" 0) (mode_tile "wale_tw" 0) (mode_tile "wale_tf" 0)
        )
        (progn (mode_tile "wale_h" 1) (mode_tile "wale_b" 1) (mode_tile "wale_tw" 1) (mode_tile "wale_tf" 1))
      )
      (set_tile "ctc" (rtos *tsp-ctc* 2 2))
      (set_tile "timber_thickness" (itoa *tsp-timber-thickness*))
      ;; 3. 액션 처리 (std-len 변수를 사용하여 동적으로 처리)
      (action_tile "hpile_spec" "(if (= (atoi $value) std-len) (progn (mode_tile \"hpile_h\" 0)(mode_tile \"hpile_b\" 0)(mode_tile \"hpile_tw\" 0)(mode_tile \"hpile_tf\" 0)) (progn (mode_tile \"hpile_h\" 1)(mode_tile \"hpile_b\" 1)(mode_tile \"hpile_tw\" 1)(mode_tile \"hpile_tf\" 1)))")
      (action_tile "wale_spec" "(if (= (atoi $value) std-len) (progn (mode_tile \"wale_h\" 0)(mode_tile \"wale_b\" 0)(mode_tile \"wale_tw\" 0)(mode_tile \"wale_tf\" 0)) (progn (mode_tile \"wale_h\" 1)(mode_tile \"wale_b\" 1)(mode_tile \"wale_tw\" 1)(mode_tile \"wale_tf\" 1)))")
      (action_tile "accept"
        "(progn
           (setq *tsp-wall-type* \"HPILE\")
           ;; H-Pile 저장
           (setq idx (atoi (get_tile \"hpile_spec\")))
           (if (< idx std-len)
             (setq *tsp-hpile-spec* (nth idx *tsp-std-wall-list*)) ;; 리스트에서 선택
             (setq *tsp-hpile-spec* \"User-defined\" *tsp-hpile-custom* (list (atoi (get_tile \"hpile_h\")) (atoi (get_tile \"hpile_b\")) (atoi (get_tile \"hpile_tw\")) (atoi (get_tile \"hpile_tf\"))))
           )
           ;; Wale 저장
           (setq idx (atoi (get_tile \"wale_spec\")))
           (if (< idx std-len)
             (setq *tsp-wale-spec* (nth idx *tsp-std-wall-list*)) ;; 리스트에서 선택
             (setq *tsp-wale-spec* \"User-defined\" *tsp-wale-custom* (list (atoi (get_tile \"wale_h\")) (atoi (get_tile \"wale_b\")) (atoi (get_tile \"wale_tw\")) (atoi (get_tile \"wale_tf\"))))
           )
           ;; 기타 변수 저장
           (setq *tsp-ctc* (atof (get_tile \"ctc\")))
           (setq *tsp-timber-thickness* (atoi (get_tile \"timber_thickness\")))
           (done_dialog 1)
         )"
      )
      (action_tile "back" "(done_dialog 2)")
      (action_tile "cancel" "(done_dialog 0)")
      (setq result (start_dialog))
      (unload_dialog dcl-id)
      result
    )
  )
)


;;;;==========================================================================
;;;; defun brace-dialog-callback : 다단 사보강재(Corner Strut) 설정 대화상자 콜백
;;;;==========================================================================
(defun brace-dialog-callback (dcl-path temp-seg-data limits rem-count / dcl-id result temp-b-rows std-len idx res-spec res-custom input-dist abs-dist prev-dist update-brace-list i str-dist disp num-b-rows min-req next-b-row next-dist sel-idx new-list allowed-dist hard-limit soft-limit tag-str jack-list res-jack b-jack dlg-name do-proceed tmp-id seg-id-str init-data init-upg cur-wale-spec cur-wale-vals cur-wale-h update-upgrade-ui res-upg upg-idx last-auto-max-spec is-init-phase cur-idx prev-idx seg-prev seg-cur p-corner p-prev p-next a1 a2 delta internal-angle-deg warn-id warn-res skip-brace loop-brace ret-val user-input-dist user-brace-spec user-brace-jack old-view-ctr old-view-size zoom-h scr-size aspect-ratio view-w target-cx target-cy orig-seg-data did-temp-draw user-chk-upgrade user-upg-spec tmp-upg tmp-brace tmp-seg init-slender init-is-manual init-interval init-enable init-margin slender-list validate-and-close update-stiffener-ui user-res-upg sel-indices user-brace-conn conn-list res-conn b-conn)
  (setq seg-id-str (itoa (if (assoc 'ID temp-seg-data) (cdr (assoc 'ID temp-seg-data)) 0)))
  (setq init-data (cdr (assoc 'CORNER-BRACE temp-seg-data)))
  (setq init-upg (cdr (assoc 'UPGRADE-WALE temp-seg-data)))
  (setq cur-wale-spec (cdr (assoc 'WALE-SPEC temp-seg-data)))
  (setq cur-wale-vals (if (= cur-wale-spec "User-defined") (cdr (assoc 'WALE-CUSTOM temp-seg-data)) (parse-h-spec cur-wale-spec)))
  (setq cur-wale-h (if cur-wale-vals (nth 0 cur-wale-vals) 300))

  (setq cur-idx (1- (if (assoc 'ID temp-seg-data) (cdr (assoc 'ID temp-seg-data)) 1)))
  (setq prev-idx (if (= cur-idx 0) (1- (length *segment-list*)) (1- cur-idx)))
  
  (setq seg-prev (if (and (>= prev-idx 0) (< prev-idx (length *segment-list*))) (nth prev-idx *segment-list*) nil))
  (setq seg-cur temp-seg-data)
  
  (setq p-corner (cdr (assoc 'V-START seg-cur)))
  (setq p-prev (if seg-prev (cdr (assoc 'V-START seg-prev)) nil))
  (setq p-next (cdr (assoc 'V-END seg-cur)))

  (setq internal-angle-deg 90.0)
  (if (and p-corner p-prev p-next)
    (progn
      (setq a1 (angle p-corner p-prev))
      (setq a2 (angle p-corner p-next))
      (setq delta (abs (- a1 a2)))
      (if (> delta pi) (setq delta (- (* 2.0 pi) delta)))
      (setq internal-angle-deg (* delta (/ 180.0 pi)))
    )
  )
  
  (princ (strcat "\n " seg-id-str "번 모서리의 실제 계산된 사이각: " (rtos internal-angle-deg 2 2) "도"))

  (setq skip-brace nil warn-res 0)
  (if (and (or (null (cadr init-data)) (= (length (cadr init-data)) 0)) 
           (>= internal-angle-deg 119.5))
    (progn
      (setq warn-id (load_dialog dcl-path))
      (if (and warn-id (new_dialog "tsp_brace_angle_warn" warn-id))
        (progn
          (set_tile "angle_msg" (strcat "코너 각도가 " (rtos internal-angle-deg 2 1) "도 입니다."))
          (action_tile "btn_skip" "(done_dialog 1)")
          (action_tile "btn_cont" "(done_dialog 2)")
          (setq warn-res (start_dialog))
          (unload_dialog warn-id)
        )
        (if warn-id (unload_dialog warn-id))
      )
      (if (/= warn-res 2) (setq skip-brace T))
    )
  )

  (if skip-brace
        (list (if (and rem-count (= rem-count 1)) "COMP" "NEXT") '("N" nil) init-upg)
        (progn
          (setq hard-limit (car limits))
          (setq soft-limit (cadr limits))
          
          (setq full-brace-list (append *tsp-std-wall-list* (mapcar '(lambda (x) (vl-string-subst "2H " "H " x)) *tsp-std-wall-list*)))
          
          ;;;;==========================================================================
          ;;;; defun get-auto-spec : 허용 길이 초과 여부를 검사하여 필요시 2H로 자동 변환
          ;;;;==========================================================================
          (defun get-auto-spec (base-spec base-custom target-dist is-mod / limit-val act-wale-h real-d real-t-L l-m)
            (setq limit-val (if (= (get_tile "slenderness_limit") "0") 100.0 120.0))
            (setq act-wale-h cur-wale-h)
            (if (= (get_tile "chk_upgrade_wale") "1")
              (setq act-wale-h (nth 0 (parse-h-spec (nth (atoi (get_tile "upgrade_wale_spec")) *tsp-std-wall-list*))))
            )
            (setq real-d (max 0.0 (- target-dist (/ act-wale-h 1000.0))))
              (setq real-t-L (* real-d (sqrt (* 2.0 (- 1.0 (cos (* internal-angle-deg (/ pi 180.0))))))))
              (setq l-m (tsp-calc-unsupported-length base-custom limit-val))
             
              ;; [추가] 25m 자중 좌굴 한계 초과 경고 (Soft Warning)
              (if (and (> real-t-L 25.0) (wcmatch base-spec "*H*"))
                (if (not *tsp-brace-buckle-warned*)
                  (progn
                    (alert (strcat "경고: 사보강재의 예상 길이(" (rtos real-t-L 2 1) "m)가 자중 좌굴 한계(25m)를 초과합니다.\n안전성에 유의하여 작도를 진행합니다."))
                    (setq *tsp-brace-buckle-warned* T)
                  )
                )
              )

              (if (and (> real-t-L l-m) (wcmatch base-spec "H *"))
                (if is-mod
                  ;; 수정(Mod) 모드일 때: 사용자가 1겹(H)을 강제로 선택한 경우
                  (progn
                    (if (not *tsp-warned-flag*)
                      (progn
                        (alert "경고: 사보강재의 최대 길이가 세장비 허용 한계를 초과합니다!\n안전을 위해 맞버팀대(2H)가 권장되나, 사용자의 요청에 의해 1겹(H)으로 강제 적용됩니다.\n구조 검토를 반드시 확인하세요.")
                        (setq *tsp-warned-flag* T)
                      )
                    )
                    base-spec ; H로 강제 유지
                  )
                  ;; 추가(Add) 모드일 때: 기존처럼 2H로 안전하게 자동 치환
                  (vl-string-subst "2H " "H " base-spec)
                )
                base-spec
              )
            )

          (setq old-view-ctr (getvar "VIEWCTR"))
      (setq old-view-size (getvar "VIEWSIZE"))
      (if p-corner
        (progn
          (setq zoom-h (* (if (> hard-limit 1.0) hard-limit 5.0) 1000.0 3.0))
          (setq scr-size (getvar "SCREENSIZE"))
          (setq aspect-ratio (/ (car scr-size) (cadr scr-size)))
          (setq view-w (* zoom-h aspect-ratio))
          (setq target-cx (- (car p-corner) (* view-w 0.3)))
          (setq target-cy (cadr p-corner))
          (command "_.ZOOM" "_C" (list target-cx target-cy) zoom-h)
        )
      )

      (if (and init-data (= (car init-data) "Y") (cadr init-data))
        (setq temp-b-rows (cadr init-data))
        (setq temp-b-rows '())
      )
      
      (setq init-slender (if (> (length init-data) 2) (nth 2 init-data) "1"))
      (setq init-is-manual (if (> (length init-data) 3) (nth 3 init-data) "0"))
      (setq init-interval (if (> (length init-data) 4) (nth 4 init-data) "0.0"))
      (setq init-enable (if (> (length init-data) 5) (nth 5 init-data) "1"))
      (setq init-margin (if (> (length init-data) 6) (nth 6 init-data) "50"))
      (setq init-post-enable (if (> (length init-data) 7) (nth 7 init-data) "0"))
      (setq init-post-side (if (> (length init-data) 8) (nth 8 init-data) "L"))
      (setq init-post-layout (if (> (length init-data) 9) (nth 9 init-data) "1"))
      (setq init-post-invert (if (> (length init-data) 10) (nth 10 init-data) "0"))

      (setq dlg-name (if (and rem-count (= rem-count 0)) "tsp_brace_single" "tsp_brace"))
      
      (setq user-input-dist nil user-brace-spec nil user-brace-jack nil user-brace-conn nil)
      (setq orig-seg-data (nth cur-idx *segment-list*))
      (setq did-temp-draw nil)

      ;; 취소 시 복원을 위한 임시 세션 데이터 초기화
      (setq *tsp-temp-added-posts* (vlax-ldata-get "TSP_DICT" "ADDED_POSTS"))
      (if (not *tsp-temp-added-posts*) (setq *tsp-temp-added-posts* '()))
      (setq *tsp-temp-deleted-posts* (vlax-ldata-get "TSP_DICT" "DELETED_POSTS"))
      (if (not *tsp-temp-deleted-posts*) (setq *tsp-temp-deleted-posts* '()))
      (setq *tsp-use-temp-posts* T)

      (setq loop-brace T ret-val nil)
      (setq *tsp-brace-buckle-warned* nil) ; 25m 자중 좌굴 경고 플래그 초기화

      (while loop-brace
        (setq dcl-id (load_dialog dcl-path))
        (if (new_dialog dlg-name dcl-id)
          (progn
            (set_tile "brace_dlg_title" (strcat seg-id-str "번 모서리 사보강재(Corner Strut) 설정"))
            (set_tile "brace_info" (strcat "▶ 절대 한계: " (rtos hard-limit 2 2) "m / 권장(50%): " (rtos soft-limit 2 2) "m"))
            (start_list "brace_spec")
            ;; 맞버팀대(2H)가 포함된 확장 리스트를 드롭다운에 출력
            (mapcar 'add_list (append full-brace-list '("User-defined")))
            (end_list)
            (setq std-len (length full-brace-list))
            (setq jack-list '("스크류잭" "유압잭"))
            (start_list "brace_jack") (mapcar 'add_list jack-list) (end_list)
            (setq conn-list '("화타쐐기 없음" "화타쐐기 TYPE-G1"))
            (start_list "brace_conn") (mapcar 'add_list conn-list) (end_list)
            
            (setq slender-list '("100 (표준 기준)" "120 (최대 예외 한계)"))
            (start_list "slenderness_limit") (mapcar 'add_list slender-list) (end_list)
            
            ;; 추가된 UI 초기값 설정
            (set_tile "chk_stiffener_enable" init-enable)
            (set_tile "slenderness_limit" init-slender)
            (set_tile "chk_manual_interval" init-is-manual)
            (set_tile "stiffener_interval" init-interval)
            (set_tile "stiffener_margin" init-margin)
            (set_tile "chk_post_enable" init-post-enable)
            (if (= init-post-side "R") (set_tile "post_side_R" "1") (set_tile "post_side_L" "1"))
            (start_list "post_layout_mode") (mapcar 'add_list '("전체 배치" "교차 배치")) (end_list)
            (set_tile "post_layout_mode" init-post-layout)
            
            ;; 교차 반전 토글 초기화 및 활성/비활성 제어
            (set_tile "chk_post_invert" init-post-invert)
            (if (= init-post-layout "1") (mode_tile "chk_post_invert" 0) (mode_tile "chk_post_invert" 1))

            ;; 배치 옵션 및 교차 반전 토글 클릭 시 실시간 갱신을 위해 데이터 캡처 후 (done_dialog 5) 호출
            (action_tile "post_layout_mode" "(progn (setq init-post-layout $value) (if (= $value \"1\") (mode_tile \"chk_post_invert\" 0) (progn (mode_tile \"chk_post_invert\" 1) (set_tile \"chk_post_invert\" \"0\") (setq init-post-invert \"0\"))) (setq user-input-dist (get_tile \"brace_dist\")) (setq user-brace-spec (get_tile \"brace_spec\")) (setq user-brace-jack (get_tile \"brace_jack\")) (setq user-brace-conn (get_tile \"brace_conn\")) (setq user-chk-upgrade (get_tile \"chk_upgrade_wale\")) (setq user-upg-spec (get_tile \"upgrade_wale_spec\")) (setq init-slender (get_tile \"slenderness_limit\")) (setq init-is-manual (get_tile \"chk_manual_interval\")) (setq init-interval (get_tile \"stiffener_interval\")) (setq init-enable (get_tile \"chk_stiffener_enable\")) (setq init-margin (get_tile \"stiffener_margin\")) (setq init-post-enable (get_tile \"chk_post_enable\")) (setq init-post-side (if (= (get_tile \"post_side_R\") \"1\") \"R\" \"L\")) (done_dialog 5))")
            (action_tile "chk_post_invert" "(progn (setq init-post-invert $value) (setq user-input-dist (get_tile \"brace_dist\")) (setq user-brace-spec (get_tile \"brace_spec\")) (setq user-brace-jack (get_tile \"brace_jack\")) (setq user-brace-conn (get_tile \"brace_conn\")) (setq user-chk-upgrade (get_tile \"chk_upgrade_wale\")) (setq user-upg-spec (get_tile \"upgrade_wale_spec\")) (setq init-slender (get_tile \"slenderness_limit\")) (setq init-is-manual (get_tile \"chk_manual_interval\")) (setq init-interval (get_tile \"stiffener_interval\")) (setq init-enable (get_tile \"chk_stiffener_enable\")) (setq init-margin (get_tile \"stiffener_margin\")) (setq init-post-enable (get_tile \"chk_post_enable\")) (setq init-post-side (if (= (get_tile \"post_side_R\") \"1\") \"R\" \"L\")) (setq init-post-layout (get_tile \"post_layout_mode\")) (done_dialog 5))")

            (start_list "upgrade_wale_spec") (mapcar 'add_list *tsp-std-wall-list*) (end_list)
            
            ;; 도면 미리보기 후 다이얼로그 복귀 시, 사용자가 조작했던 상향 설정값을 잃지 않고 우선 복원
            (if user-chk-upgrade
              (progn
                (set_tile "chk_upgrade_wale" user-chk-upgrade)
                (if user-upg-spec
                  (set_tile "upgrade_wale_spec" user-upg-spec)
                )
              )
              (if init-upg
                (progn
                  (set_tile "chk_upgrade_wale" (if (= (car init-upg) "Y") "1" "0"))
                  (if (setq upg-idx (vl-position (cadr init-upg) *tsp-std-wall-list*))
                    (set_tile "upgrade_wale_spec" (itoa upg-idx)) (set_tile "upgrade_wale_spec" "2")
                  )
                )
                (progn (set_tile "chk_upgrade_wale" "0") (set_tile "upgrade_wale_spec" "2"))
              )
            )
            
            (defun update-upgrade-ui (/ max-h max-spec check-h b-idx check-vals spec-idx)
              (setq max-h 0 max-spec nil)
              (foreach b temp-b-rows
                (setq check-h (nth 0 (cadr b)))
                (if (> check-h max-h) (progn (setq max-h check-h) (setq max-spec (car b))))
              )
              (setq b-idx (atoi (get_tile "brace_spec")))
              (if (< b-idx std-len)
                (progn
                  ;; 2H 규격이더라도 파서가 에러를 내지 않도록 "H "로 임시 치환하여 치수 검사
                  (setq check-vals (parse-h-spec (vl-string-subst "H " "2H " (nth b-idx full-brace-list))))
                  (if (and check-vals (> (nth 0 check-vals) max-h))
                    (progn (setq max-h (nth 0 check-vals)) (setq max-spec (nth b-idx full-brace-list)))
                  )
                )
                (progn
                  (setq check-vals (list (atoi (get_tile "brace_h")) 0 0 0))
                  (if (> (nth 0 check-vals) max-h)
                    (progn (setq max-h (nth 0 check-vals)) (setq max-spec "User-defined"))
                  )
                )
              )
              (if (> max-h cur-wale-h)
                (progn
                  (mode_tile "chk_upgrade_wale" 0)
                  (mode_tile "upgrade_wale_spec" 0)
                  (if (not (equal last-auto-max-spec max-spec))
                    (progn
                      (if (not is-init-phase)
                        (progn
                          (set_tile "chk_upgrade_wale" "1")
                          (if (and max-spec (/= max-spec "User-defined") (setq spec-idx (vl-position max-spec *tsp-std-wall-list*)))
                            (set_tile "upgrade_wale_spec" (itoa spec-idx))
                          )
                        )
                      )
                      (setq last-auto-max-spec max-spec)
                    )
                  )
                )
                (progn
                  (mode_tile "chk_upgrade_wale" 1)
                  (mode_tile "upgrade_wale_spec" 1)
                  (set_tile "chk_upgrade_wale" "0")
                  (setq last-auto-max-spec nil)
                )
              )
            )

;;;;==========================================================================
;;;; defun update-stiffener-ui : 사보강재 간격 및 세장비 계산 UI 업데이트
;;;;==========================================================================
            (defun update-stiffener-ui (/ limit-val is-manual b-custom max-dist L-max real-dist real-total-L num-div req-interval str-L ang-rad last-row is-enabled active-wale-h upg-idx)
              (setq is-enabled (get_tile "chk_stiffener_enable"))
              (if (= is-enabled "0")
                (progn
                  (mode_tile "slenderness_limit" 1)
                  (mode_tile "chk_manual_interval" 1)
                  (mode_tile "stiffener_interval" 1)
                  (mode_tile "stiffener_margin" 1)
                  (set_tile "stiffener_info" "보강재 배열 생성 생략 (사보강재 메인 프레임만 생성)")
                )
                (progn
                  (mode_tile "slenderness_limit" 0)
                  (mode_tile "chk_manual_interval" 0)
                  (mode_tile "stiffener_margin" 0)
                  
                  (setq limit-val (if (= (get_tile "slenderness_limit") "0") 100.0 120.0))
                  (setq is-manual (get_tile "chk_manual_interval"))
                  (if (= is-manual "1") (mode_tile "stiffener_interval" 0) (mode_tile "stiffener_interval" 1))

                  (if (and temp-b-rows (> (length temp-b-rows) 0))
                    (progn
                      (setq last-row (last temp-b-rows))
                      (setq b-custom (nth 1 last-row))
                      (setq max-dist (nth 2 last-row))
                      (setq ang-rad (* internal-angle-deg (/ pi 180.0)))
                      
                      ;; 1. 현재 적용될 띠장(Wale)의 H(높이)값 동적 추출
                      (setq active-wale-h cur-wale-h)
                      (if (= (get_tile "chk_upgrade_wale") "1")
                        (progn
                          (setq upg-idx (atoi (get_tile "upgrade_wale_spec")))
                          (if (< upg-idx std-len)
                            (setq active-wale-h (nth 0 (parse-h-spec (nth upg-idx *tsp-std-wall-list*))))
                          )
                        )
                      )
                      
                      ;; 2. 이격거리에서 띠장 두께(H)를 뺀 실질 이격거리 산출
                      (setq real-dist (max 0.0 (- max-dist (/ active-wale-h 1000.0))))
                      
                      ;; 3. 최대 사보강재 길이 산출 (실질 이격거리 기준 기하학적 길이)
                      (setq real-total-L (* real-dist (sqrt (* 2.0 (- 1.0 (cos ang-rad))))))

                      ;; 4. 실제 길이(real-total-L)를 기준으로 세장비 및 등분 계산
                      (setq L-max (tsp-calc-unsupported-length b-custom limit-val))
                      (setq num-div (fix (+ (/ real-total-L L-max) 0.9999)))
                      (if (< num-div 1) (setq num-div 1))
                      (setq req-interval (/ real-total-L num-div))

                      (setq str-L (strcat "최대 사보강재 길이: " (rtos real-total-L 2 3) "m / 허용: " (rtos L-max 2 1) "m"))
                      (if (> num-div 1)
                        (set_tile "stiffener_info" (strcat str-L " -> " (itoa num-div) "등분 (" (rtos req-interval 2 2) "m)"))
                        (set_tile "stiffener_info" (strcat str-L " -> 보강재 불필요"))
                      )
                      (if (= is-manual "0")
                        (set_tile "stiffener_interval" (rtos req-interval 2 2))
                      )
                    )
                    (set_tile "stiffener_info" "사보강재(Corner Strut)를 먼저 추가하세요.")
                  )
                )
              )
            )


;;;;==========================================================================
;;;; defun update-brace-list : 사보강재 리스트 갱신 및 다음 열 입력용 연결방식 콤보박스 자동 제어 기능
;;;;==========================================================================
            (defun update-brace-list (/ i prev item spec m-dist rel-dist disp tag-str b-jack b-conn)
              (start_list "brace_list")
              (setq i 0 prev 0.0)
              (foreach item temp-b-rows
                (setq spec (car item) m-dist (nth 2 item) b-jack (nth 3 item) b-conn (nth 4 item))
                (if (null b-jack) (setq b-jack "스크류잭"))
                (if (null b-conn) (setq b-conn (if (= i 0) "화타쐐기 없음" "화타쐐기 TYPE-G1")))
                (setq rel-dist (- m-dist prev))
                (if (> m-dist hard-limit)
                  (setq tag-str "  [!] 절대 한계 초과")
                  (if (> m-dist soft-limit) (setq tag-str "  [!] 권장 한계 초과") (setq tag-str ""))
                )
                (if (= i 0)
                  (setq disp (strcat (itoa (1+ i)) "열: " spec " [" b-conn "] / " (rtos m-dist 2 2) "m" tag-str))
                  (setq disp (strcat (itoa (1+ i)) "열: " spec " (" b-jack ") [" b-conn "] / +" (rtos rel-dist 2 2) "m (누적 " (rtos m-dist 2 2) "m)" tag-str))
                )
                (add_list disp)
                (setq prev m-dist i (1+ i))
              )
              (end_list)
              (update-stiffener-ui) ; 갱신마다 예측값 및 활성상태 반영
              
              ;; 사용자가 연결방식을 수동 조작했다면 자동 전환 일시 중단
              (if (= (length temp-b-rows) 0)
                (progn
                  (set_tile "brace_conn" "0") ; 목록이 비어있으면 1열용 "화타쐐기 없음" 자동 선택
                  (setq is-conn-touched nil)  ; 초기화 상태이므로 수동 조작 기록 완벽히 리셋
                )
                (if (not is-conn-touched)
                  (set_tile "brace_conn" "1") ; 수동 조작이 없을 때만 "화타쐐기 TYPE-G1" 자동 선택
                )
              )
            )

            (update-brace-list)
            
            (if user-input-dist 
              (set_tile "brace_dist" user-input-dist) 
              (if (>= hard-limit 1.5) (set_tile "brace_dist" "1.5") (set_tile "brace_dist" "1.0"))
            )
            (set_tile "brace_spec" (if user-brace-spec user-brace-spec "2"))
            (set_tile "brace_jack" (if user-brace-jack user-brace-jack "0"))
            ;; 초기화 시에도 사용자의 이전 수동 조작값을 기억하되, 없을 경우 열 개수에 따른 자동 로직 따름
            (set_tile "brace_conn" (if user-brace-conn user-brace-conn (if (> (length temp-b-rows) 0) "1" "0")))
            
            (mode_tile "brace_h" 1) (mode_tile "brace_b" 1) (mode_tile "brace_tw" 1) (mode_tile "brace_tf" 1)
            (action_tile "brace_spec" 
              (strcat 
                "(if (= (atoi $value) std-len) "
                "  (progn (mode_tile \"brace_h\" 0)(mode_tile \"brace_b\" 0)(mode_tile \"brace_tw\" 0)(mode_tile \"brace_tf\" 0)) "
                "  (progn (mode_tile \"brace_h\" 1)(mode_tile \"brace_b\" 1)(mode_tile \"brace_tw\" 1)(mode_tile \"brace_tf\" 1))) "
                "(if (wcmatch (nth (atoi $value) full-brace-list) \"2H *\") "
                "  (if (< (atof (get_tile \"brace_dist\")) 2.0) (set_tile \"brace_dist\" \"2.0\"))) "
                "(update-upgrade-ui)"
              )
            )
            (action_tile "brace_h" "(update-upgrade-ui)")
            
            ;; 연결방식 콤보박스 수동 조작 감지 스위치 켜기
            (action_tile "brace_conn" "(setq is-conn-touched T)")
            
            ;; UI 액션 콜백 할당
            (action_tile "chk_stiffener_enable" "(update-stiffener-ui)")
            (action_tile "slenderness_limit" "(update-stiffener-ui)")
            (action_tile "chk_manual_interval" "(update-stiffener-ui)")

            (setq is-init-phase T)
            (update-upgrade-ui)
            (setq is-init-phase nil)

            (action_tile "btn_measure"
              "(progn 
                 (setq user-input-dist (get_tile \"brace_dist\"))
                 (setq user-brace-spec (get_tile \"brace_spec\"))
                 (setq user-brace-jack (get_tile \"brace_jack\"))
                 (setq user-brace-conn (get_tile \"brace_conn\"))
                 (setq user-chk-upgrade (get_tile \"chk_upgrade_wale\"))
                 (setq user-upg-spec (get_tile \"upgrade_wale_spec\"))
                 (setq init-slender (get_tile \"slenderness_limit\"))
                 (setq init-is-manual (get_tile \"chk_manual_interval\"))
                 (setq init-interval (get_tile \"stiffener_interval\"))
                 (setq init-enable (get_tile \"chk_stiffener_enable\"))
                 (setq init-margin (get_tile \"stiffener_margin\"))
                 (setq init-post-enable (get_tile \"chk_post_enable\"))
                 (setq init-post-side (if (= (get_tile \"post_side_R\") \"1\") \"R\" \"L\"))
                 (setq init-post-layout (get_tile \"post_layout_mode\"))
                 (setq init-post-invert (get_tile \"chk_post_invert\"))
                 (done_dialog 5)
               )"
            )

            (action_tile "btn_add"
              (strcat
                "(progn (setq input-dist (atof (get_tile \"brace_dist\"))) (setq num-b-rows (length temp-b-rows)) (setq prev-dist (if (> num-b-rows 0) (nth 2 (last temp-b-rows)) 0.0)) (setq abs-dist (+ prev-dist input-dist)) "
                "(setq is-dbl-sel (wcmatch (if (< (atoi (get_tile \"brace_spec\")) std-len) (nth (atoi (get_tile \"brace_spec\")) full-brace-list) \"\") \"2H *\")) "
                "(setq min-req (if is-dbl-sel (if (= num-b-rows 0) 1.5 1.2) (if (= num-b-rows 0) 1.0 0.8))) "
                "(if (< input-dist min-req) "
                "  (if is-dbl-sel "
                "    (if (= num-b-rows 0) (alert (strcat \"맞버팀대(2H) 1열은 코너부 간섭을 피하기 위해 최소 \" (rtos min-req 2 1) \"m 이상 이격해야 합니다.\")) (alert (strcat \"맞버팀대(2H) 다중열 설치 시 부재 간 간섭 방지를 위해 최소 \" (rtos min-req 2 1) \"m 이상 이격해야 합니다.\"))) "
                "    (if (= num-b-rows 0) (alert (strcat \"1열 사보강재(Corner Strut)는 여유 공간을 위해 최소 \" (rtos min-req 2 1) \"m 이상 이격해야 합니다.\")) (alert (strcat \"여러 열 설치 시 부재 간 간섭 방지를 위해 최소 \" (rtos min-req 2 1) \"m 이상 이격해야 합니다.\"))) "
                "  ) "
                "(progn (setq do-proceed T) (if (> abs-dist hard-limit) (progn (setq tmp-id (load_dialog dcl-path)) (if (new_dialog \"tsp_brace_hard_warn\" tmp-id) (progn (if (< hard-limit min-req) (progn (set_tile \"warn_msg1\" (strcat \"물리적 여유 공간(\" (rtos hard-limit 2 2) \"m)이 최소 기준(\" (rtos min-req 2 1) \"m) 부족입니다.\")) (set_tile \"warn_msg2\" \"시공 불가 예상 구간이나, 이대로 강제 돌파(적용)하시겠습니까?\"))) (action_tile \"accept\" \"(done_dialog 1)\") (action_tile \"cancel\" \"(done_dialog 0)\") (if (= (start_dialog) 0) (setq do-proceed nil)))) (unload_dialog tmp-id)) "
                "(if (> abs-dist soft-limit) (progn (setq tmp-id (load_dialog dcl-path)) (if (new_dialog \"tsp_brace_warn\" tmp-id) (progn (action_tile \"accept\" \"(done_dialog 1)\") (action_tile \"cancel\" \"(done_dialog 0)\") (if (= (start_dialog) 0) (setq do-proceed nil)))) (unload_dialog tmp-id)))) "
                "(if do-proceed (progn (setq idx (atoi (get_tile \"brace_spec\"))) (if (< idx std-len) (progn (setq res-spec (nth idx full-brace-list)) (setq res-custom (parse-h-spec (vl-string-subst \"H \" \"2H \" res-spec)))) (progn (setq res-spec \"User-defined\") (setq res-custom (list (atoi (get_tile \"brace_h\")) (atoi (get_tile \"brace_b\")) (atoi (get_tile \"brace_tw\")) (atoi (get_tile \"brace_tf\")))))) "
                "(setq tmp-spec (get-auto-spec res-spec res-custom abs-dist nil)) "
                "(if (and (wcmatch tmp-spec \"2H *\") (not (wcmatch res-spec \"2H *\")) (< input-dist 2.0)) "
                "  (progn "
                "    (setq input-dist 2.0) "
                "    (setq abs-dist (+ prev-dist input-dist)) "
                "    (set_tile \"brace_dist\" \"2.0\") "
                "    (alert \"세장비 허용 한계를 초과하여 맞버팀대(2H)로 자동 전환되었으며, 공간 확보를 위해 이격거리가 2.0m로 자동 보정되었습니다.\") "
                "  ) "
                ") "
                "(setq res-spec tmp-spec) "
                "(setq res-jack (nth (atoi (get_tile \"brace_jack\")) jack-list)) (setq res-conn (nth (atoi (get_tile \"brace_conn\")) conn-list)) (setq temp-b-rows (append temp-b-rows (list (list res-spec res-custom abs-dist res-jack res-conn)))) (update-brace-list) (update-upgrade-ui) )))))"
              )
            )
            
            (action_tile "btn_mod"
              (strcat
                "(progn (setq *tsp-warned-flag* nil *tsp-brace-buckle-warned* nil) (setq sel-idx-str (get_tile \"brace_list\")) (setq sel-indices (if (and sel-idx-str (/= sel-idx-str \"\")) (tsp-parse-space-string sel-idx-str) nil)) "
                "(if sel-indices (progn "
                "(setq idx (atoi (get_tile \"brace_spec\"))) (if (< idx std-len) (progn (setq res-spec (nth idx full-brace-list)) (setq res-custom (parse-h-spec (vl-string-subst \"H \" \"2H \" res-spec)))) (progn (setq res-spec \"User-defined\") (setq res-custom (list (atoi (get_tile \"brace_h\")) (atoi (get_tile \"brace_b\")) (atoi (get_tile \"brace_tw\")) (atoi (get_tile \"brace_tf\")))))) "
                "(setq res-jack (nth (atoi (get_tile \"brace_jack\")) jack-list)) (setq res-conn (nth (atoi (get_tile \"brace_conn\")) conn-list)) "
                "(if (= (length sel-indices) 1) (progn "
                "(setq sel-idx (car sel-indices)) (setq input-dist (atof (get_tile \"brace_dist\"))) (setq prev-dist (if (> sel-idx 0) (nth 2 (nth (1- sel-idx) temp-b-rows)) 0.0)) (setq abs-dist (+ prev-dist input-dist)) "
                "(setq is-dbl-sel (wcmatch res-spec \"2H *\")) "
                "(setq min-req (if is-dbl-sel (if (= sel-idx 0) 1.5 1.2) (if (= sel-idx 0) 1.0 0.8))) "
                "(setq next-b-row (if (< (1+ sel-idx) (length temp-b-rows)) (nth (1+ sel-idx) temp-b-rows) nil)) (setq next-dist (if next-b-row (nth 2 next-b-row) nil)) "
                "(if (< input-dist min-req) "
                "  (if is-dbl-sel "
                "    (if (= sel-idx 0) (alert (strcat \"맞버팀대(2H) 1열은 코너부 간섭을 피하기 위해 최소 \" (rtos min-req 2 1) \"m 이상 이격해야 합니다.\")) (alert (strcat \"맞버팀대(2H) 다중열 설치 시 부재 간 간섭 방지를 위해 최소 \" (rtos min-req 2 1) \"m 이상 이격해야 합니다.\"))) "
                "    (if (= sel-idx 0) (alert (strcat \"1열 사보강재(Corner Strut)는 여유 공간을 위해 최소 \" (rtos min-req 2 1) \"m 이상 이격해야 합니다.\")) (alert (strcat \"여러 열 설치 시 부재 간 간섭 방지를 위해 최소 \" (rtos min-req 2 1) \"m 이상 이격해야 합니다.\"))) "
                "  ) "
                "(if (and next-dist (< (- next-dist abs-dist) 0.8)) (alert \"수정 시 다음 열과의 간격이 0.8m 미만이 되어 간섭이 발생합니다. 다음 열을 먼저 수정하거나 거리를 조절하세요.\") (progn (setq do-proceed T) (if (> abs-dist hard-limit) (progn (setq tmp-id (load_dialog dcl-path)) (if (new_dialog \"tsp_brace_hard_warn\" tmp-id) (progn (if (< hard-limit min-req) (progn (set_tile \"warn_msg1\" (strcat \"물리적 여유 공간(\" (rtos hard-limit 2 2) \"m)이 최소 기준(\" (rtos min-req 2 1) \"m) 부족입니다.\")) (set_tile \"warn_msg2\" \"시공 불가 예상 구간이나, 이대로 강제 돌파(적용)하시겠습니까?\"))) (action_tile \"accept\" \"(done_dialog 1)\") (action_tile \"cancel\" \"(done_dialog 0)\") (if (= (start_dialog) 0) (setq do-proceed nil)))) (unload_dialog tmp-id)) "
                "(if (> abs-dist soft-limit) (progn (setq tmp-id (load_dialog dcl-path)) (if (new_dialog \"tsp_brace_warn\" tmp-id) (progn (action_tile \"accept\" \"(done_dialog 1)\") (action_tile \"cancel\" \"(done_dialog 0)\") (if (= (start_dialog) 0) (setq do-proceed nil)))) (unload_dialog tmp-id)))) "
                "(if do-proceed (progn (setq tmp-spec (get-auto-spec res-spec res-custom abs-dist T)) (setq i 0 new-list '()) (foreach item temp-b-rows (if (= i sel-idx) (setq new-list (append new-list (list (list tmp-spec res-custom abs-dist res-jack res-conn)))) (setq new-list (append new-list (list item)))) (setq i (1+ i))) (setq temp-b-rows new-list) (update-brace-list) (update-upgrade-ui) )))))) "
                "(progn (setq i 0 new-list '()) (foreach item temp-b-rows (if (vl-position i sel-indices) (progn (setq cur-abs-dist (nth 2 item)) (setq tmp-spec (get-auto-spec res-spec res-custom cur-abs-dist T)) (setq new-list (append new-list (list (list tmp-spec res-custom cur-abs-dist res-jack res-conn))))) (setq new-list (append new-list (list item)))) (setq i (1+ i))) (setq temp-b-rows new-list) (update-brace-list) (update-upgrade-ui) )) "
                ") (alert \"수정할 항목을 선택하세요!\")))"
              )
            )
            
            (action_tile "btn_del" "(progn (setq sel-idx-str (get_tile \"brace_list\")) (if (and sel-idx-str (/= sel-idx-str \"\")) (progn (setq sel-indices (tsp-parse-space-string sel-idx-str)) (setq new-list '() i 0) (foreach item temp-b-rows (if (not (vl-position i sel-indices)) (setq new-list (append new-list (list item)))) (setq i (1+ i))) (setq temp-b-rows new-list) (update-brace-list) (update-upgrade-ui)) (alert \"삭제할 항목을 선택하세요!\")))")
            
            (defun validate-and-close (done_val / limit-val b-custom L-max input-int)
              ;; 띠장 상향 데이터 소실 방지 로직 도입
              (setq user-res-upg 
                (if (= (get_tile "chk_upgrade_wale") "1") 
                  (list "Y" (nth (atoi (get_tile "upgrade_wale_spec")) *tsp-std-wall-list*) nil)
                  (if (and init-upg (= (car init-upg) "Y"))
                    init-upg ; 기존 띠장 상향 설정 보존
                    nil
                  )
                )
              )
              (setq init-enable (get_tile "chk_stiffener_enable"))
              (setq init-slender (get_tile "slenderness_limit"))
              (setq init-is-manual (get_tile "chk_manual_interval"))
              (setq init-interval (get_tile "stiffener_interval"))
              (setq init-margin (get_tile "stiffener_margin"))
              (setq init-post-enable (get_tile "chk_post_enable"))
              (setq init-post-side (if (= (get_tile "post_side_R") "1") "R" "L"))
              (setq init-post-layout (get_tile "post_layout_mode"))
              (setq init-post-invert (get_tile "chk_post_invert"))
              
              (if (and temp-b-rows (> (length temp-b-rows) 0) (= init-enable "1") (= init-is-manual "1"))
                (progn
                  (setq limit-val (if (= init-slender "0") 100.0 120.0))
                  (setq b-custom (nth 1 (last temp-b-rows)))
                  (setq L-max (tsp-calc-unsupported-length b-custom limit-val))
                  (setq input-int (atof init-interval))
                  (if (and (> input-int 0.01) (> input-int L-max))
                    (alert (strcat "입력한 수동 간격(" (rtos input-int 2 2) "m)이 세장비 허용 한계(" (rtos L-max 2 2) "m)를 초과하여 구조적으로 위험합니다. 값을 낮춰주세요."))
                    (done_dialog done_val)
                  )
                )
                (done_dialog done_val)
              )
            )

            (setq save-ui-state-str
              "(progn
                 (setq user-input-dist (get_tile \"brace_dist\"))
                 (setq user-brace-spec (get_tile \"brace_spec\"))
                 (setq user-brace-jack (get_tile \"brace_jack\"))
                 (setq user-brace-conn (get_tile \"brace_conn\"))
                 (setq user-chk-upgrade (get_tile \"chk_upgrade_wale\"))
                 (setq user-upg-spec (get_tile \"upgrade_wale_spec\"))
                 (setq init-slender (get_tile \"slenderness_limit\"))
                 (setq init-is-manual (get_tile \"chk_manual_interval\"))
                 (setq init-interval (get_tile \"stiffener_interval\"))
                 (setq init-enable (get_tile \"chk_stiffener_enable\"))
                 (setq init-margin (get_tile \"stiffener_margin\"))
                 (setq init-post-enable (get_tile \"chk_post_enable\"))
                 (setq init-post-side (if (= (get_tile \"post_side_R\") \"1\") \"R\" \"L\"))
                 (setq init-post-layout (get_tile \"post_layout_mode\"))
                 (setq init-post-invert (get_tile \"chk_post_invert\"))
               )"
            )
            (action_tile "btn_post_add" (strcat save-ui-state-str "(done_dialog 97)"))
            (action_tile "btn_post_del" (strcat save-ui-state-str "(done_dialog 98)"))
            (action_tile "btn_post_reset" (strcat save-ui-state-str "(done_dialog 99)"))

            (action_tile "btn_comp" "(validate-and-close 1)")
            (action_tile "accept" (if (and rem-count (= rem-count 1)) "(validate-and-close 1)" "(validate-and-close 2)"))
            (action_tile "cancel" "(done_dialog 0)")
            
            (setq result (start_dialog))
            (unload_dialog dcl-id)
            
            ;; 결과 저장 시 추가된 파라미터(init-enable, init-margin, init-post-enable)를 리스트에 묶어 보존
            (cond
             ((= result 1) 
               (setq ret-val (list "COMP" (if (> (length temp-b-rows) 0) (list "Y" temp-b-rows init-slender init-is-manual init-interval init-enable init-margin init-post-enable init-post-side init-post-layout init-post-invert) (list "Y" nil)) user-res-upg))
               (setq loop-brace nil)
              )
              ((= result 2) 
               (setq ret-val (list "NEXT" (if (> (length temp-b-rows) 0) (list "Y" temp-b-rows init-slender init-is-manual init-interval init-enable init-margin init-post-enable init-post-side init-post-layout init-post-invert) (list "Y" nil)) user-res-upg))
               (setq loop-brace nil)
              )
              ((= result 5)
               (setq tmp-upg (if (= user-chk-upgrade "1") (list "Y" (nth (atoi user-upg-spec) *tsp-std-wall-list*) nil) nil))
               (setq tmp-brace (if (> (length temp-b-rows) 0) (list "Y" temp-b-rows init-slender init-is-manual init-interval init-enable init-margin init-post-enable init-post-side init-post-layout init-post-invert) (list "Y" nil)))
               (setq tmp-seg (subst (cons 'CORNER-BRACE tmp-brace) (assoc 'CORNER-BRACE temp-seg-data) temp-seg-data))
               (setq tmp-seg (subst (cons 'UPGRADE-WALE tmp-upg) (assoc 'UPGRADE-WALE tmp-seg) tmp-seg))
               (setq *segment-list* (update-list-item *segment-list* cur-idx tmp-seg))
               
               (if (and *tsp-boundary-ent* *tsp-boundary-orient*)
                 (tsp-redraw-realtime-plan *tsp-boundary-ent* *tsp-boundary-orient*)
               )
               
               (if tsp-pause-for-measurement
                 (tsp-pause-for-measurement)
                 (alert "TSP - 도면 제어 모듈이 로드되지 않았습니다.")
               )
               
               (setq *segment-list* (update-list-item *segment-list* cur-idx orig-seg-data))
               (setq did-temp-draw T)
              )

              ((or (= result 97) (= result 98) (= result 99))
               ;; 1. 현재 DCL 상태를 임시 전역 리스트(*segment-list*)에 덮어쓰기
               (setq tmp-upg (if (= user-chk-upgrade "1") (list "Y" (nth (atoi user-upg-spec) *tsp-std-wall-list*) nil) nil))
               (setq tmp-brace (if (> (length temp-b-rows) 0) (list "Y" temp-b-rows init-slender init-is-manual init-interval init-enable init-margin init-post-enable init-post-side init-post-layout init-post-invert) (list "Y" nil)))
               (setq tmp-seg (subst (cons 'CORNER-BRACE tmp-brace) (assoc 'CORNER-BRACE temp-seg-data) temp-seg-data))
               (setq tmp-seg (subst (cons 'UPGRADE-WALE tmp-upg) (assoc 'UPGRADE-WALE tmp-seg) tmp-seg))
               (setq *segment-list* (update-list-item *segment-list* cur-idx tmp-seg))

               ;; 2. 해당 수동 작도/삭제 함수 호출 (현재 세그먼트 ID를 추출하여 함수에 전달)
               (setq tmp-id (if (assoc 'ID temp-seg-data) (cdr (assoc 'ID temp-seg-data)) 0))
               (cond
                 ((= result 97)
                  (if (not (boundp 'tsp-manual-add-post)) 
                    (alert "수동 추가 함수(tsp-manual-add-post)가 로드되지 않았습니다.") 
                    (tsp-manual-add-post tmp-id)
                  )
                 )
                 ((= result 98)
                  (if (not (boundp 'tsp-manual-delete-post)) 
                    (alert "수동 삭제 함수(tsp-manual-delete-post)가 로드되지 않았습니다.") 
                    (tsp-manual-delete-post tmp-id)
                  )
                 )
                 ((= result 99)
                  (if (not (boundp 'tsp-delete-manual-post-by-segment)) 
                    (alert "개별 초기화 함수(tsp-delete-manual-post-by-segment)가 로드되지 않았습니다.") 
                    (progn
                      (tsp-delete-manual-post-by-segment tmp-id)
                      (princ (strcat "\n[초기화] Seg-" (itoa tmp-id) " 구역의 수동 중간말뚝이 초기화되었습니다."))
                      ;; [버그A-2 수정] 초기화 직후 도면 즉시 갱신
                      (if (and (boundp '*tsp-boundary-ent*) *tsp-boundary-ent*
                               (boundp '*tsp-boundary-orient*) *tsp-boundary-orient*)
                        (tsp-redraw-realtime-plan *tsp-boundary-ent* *tsp-boundary-orient*)
                      )
                    )
                  )
                 )
               )

               ;; 3. 원래 세그먼트 데이터로 원상복구 (사용자가 최종 취소를 누를 경우를 대비한 오염 방지)
               (setq *segment-list* (update-list-item *segment-list* cur-idx orig-seg-data))
               (setq did-temp-draw T)
              )
              (t 
               (setq ret-val nil)
               (setq loop-brace nil)
              )
            )
          )
          (progn (if dcl-id (unload_dialog dcl-id)) (setq ret-val nil loop-brace nil))
        )
      ) ;; end while loop-brace
      
      ;; 1. 확인(COMP/NEXT)을 눌렀을 때만 임시 데이터를 영구 LDATA에 반영
      (if ret-val
        (progn
          (vlax-ldata-put "TSP_DICT" "ADDED_POSTS" *tsp-temp-added-posts*)
          (vlax-ldata-put "TSP_DICT" "DELETED_POSTS" *tsp-temp-deleted-posts*)
        )
      )
      (setq *tsp-use-temp-posts* nil) ;; 임시 세션 종료
      
      (if (and old-view-ctr old-view-size)
        (command "_.ZOOM" "_C" old-view-ctr old-view-size)
      )
      
      ;; 2. 취소(Cancel)를 눌렀거나 화면 임시 갱신이 있었던 경우, 원상복구를 위해 화면 새로고침
      (if (or (null ret-val) did-temp-draw)
        (if (and *tsp-boundary-ent* *tsp-boundary-orient*)
          (tsp-redraw-realtime-plan *tsp-boundary-ent* *tsp-boundary-orient*)
        )
      )
      
      ret-val
    )
  )
)


;;;;==========================================================================
;;;; defun tsp-get-wale-offset : 특정 세그먼트의 띠장 내측면까지의 오프셋 거리 계산
;;;;==========================================================================
(defun tsp-get-wale-offset (seg-data / wall-type wale-vals wale-h wale-spec)
  (setq wall-type (cdr (assoc 'WALL-TYPE seg-data)))
  (if (not wall-type) (setq wall-type "HPILE"))
  (if (= wall-type "CIP")
    (progn
      (setq wale-spec (nth (atoi (if (cdr (assoc 'CIP-WALE-IDX seg-data)) (cdr (assoc 'CIP-WALE-IDX seg-data)) "0")) *tsp-std-wall-list*))
      (setq wale-vals (parse-h-spec wale-spec))
      (setq wale-h (if wale-vals (nth 0 wale-vals) 300.0))
      wale-h
    )
    (progn
      (setq wale-spec (cdr (assoc 'WALE-SPEC seg-data)))
      (if (null wale-spec) (setq wale-spec "H 300x300x10/15"))
      (setq wale-vals (if (= wale-spec "User-defined") (cdr (assoc 'WALE-CUSTOM seg-data)) (parse-h-spec wale-spec)))
      (setq wale-h (if wale-vals (nth 0 wale-vals) 300.0))
      wale-h
    )
  )
)


;;;;==========================================================================
;;;; defun support-dialog-callback : 지보재(Strut/Anchor) 관리 대화상자 콜백
;;;;==========================================================================
(defun support-dialog-callback (dcl-path / dcl-id result temp-supports update-support-list support-types strut-input-dialog anchor-input-dialog shape-list-strut shape-list-anchor loop-support restore-action restore-type restore-data restore-idx manual-pts pt-user p-base param1 tang tang-ang norm-ang unit-vec ray-ent int-pts pts i p p-opp param2 seg-idx1 seg-idx2 offset1 offset2 pt1 pt2 manual-drawn-ents e)
  (setq dcl-id (load_dialog dcl-path))
  (setq temp-supports (if *tsp-support-list* *tsp-support-list* '()))
  (setq support-types '("버팀보(Strut)" "앵커(Earth Anchor)"))
  (setq shape-list-strut '("H형강" "강관"))
  (setq shape-list-anchor '("Earth Anchor" "Roller Turning Anchor"))

  (setq loop-support T)
  (setq restore-action nil)
  (setq manual-drawn-ents '()) ;; 현재 창에서 임시로 작도된 객체 추적

;;==========================================================================
;; defun tsp-safe-hide-ent : 물리적 삭제(entdel) 대신 객체를 안전하게 숨기는 함수
;;==========================================================================
(defun tsp-safe-hide-ent (ent / edata)
  (if (and ent (setq edata (entget ent)))
    (if (not (assoc 60 edata))
      (vl-catch-all-apply 'entmod (list (append edata (list (cons 60 1)))))
      (vl-catch-all-apply 'entmod (list (subst (cons 60 1) (assoc 60 edata) edata)))
    )
  )
)

;;;;==========================================================================
;;;; defun strut-input-dialog : 버팀보 입력창
;;;;==========================================================================
(defun strut-input-dialog (existing-data default-name min-depth / s-result s-data mat-list-h mat-list-pipe sec-list-h sec-list-pipe update-ui-strut current-hpile-str default-h-idx jack-list jack-idx dlg-status manual-pts init-shape shape-idx saved-sec sec-list-to-search sec-idx saved-jack res-name res-shape res-depth res-count m-idx res-mat res-sec res-jack user-forced-strut-sec saved-mat mat-list-to-search def-jack strut-brace-data tmp-strut-data orig-support-list replaced new-list tmp-target-id cur-seg cur-supp-list tmp-replaced tmp-new-supp dlg-result-97 snap-added-posts snap-deleted-posts orig-segment-list unique-params xdata seg-id pt1 pt2 p-pair array-brace-opt new-ents all-pts target-seg-id strut-ang strut-len temp-brace-ents s-brace-opt)
  (setq user-forced-strut-sec nil)
  (setq mat-list-h '("SS275" "SM275" "SM355" "SM420"))
  (setq mat-list-pipe '("STP275S" "STP355S" "STP450S" "STP500S"))
  (setq sec-list-h (append *tsp-std-strut-list* (mapcar '(lambda (x) (vl-string-subst "2H " "H " x)) *tsp-std-strut-list*)))
  (setq sec-list-pipe '("D406.4x12t" "D508.0x12t" "D609.6x12t"))
  (setq jack-list '("유압잭" "스크류잭"))
  (setq current-hpile-str "")
  
  (if (and *tsp-hpile-spec* (= *tsp-hpile-spec* "User-defined") *tsp-hpile-custom*)
    (setq current-hpile-str (strcat "H " (itoa (nth 0 *tsp-hpile-custom*)) "x" (itoa (nth 1 *tsp-hpile-custom*)) "x" (itoa (nth 2 *tsp-hpile-custom*)) "/" (itoa (nth 3 *tsp-hpile-custom*))))
    (setq current-hpile-str *tsp-hpile-spec*)
  )
  (if (and current-hpile-str (/= current-hpile-str "") (not (vl-position current-hpile-str sec-list-h)))
    (setq sec-list-h (cons current-hpile-str sec-list-h))
  )
  (setq default-h-idx (vl-position "H 300x300x10/15" sec-list-h))
  (if (null default-h-idx) (setq default-h-idx 3))

  (if (new_dialog "tsp_support_strut" dcl-id)
    (progn
      (start_list "s_shape") (mapcar 'add_list shape-list-strut) (end_list)
      (start_list "s_jack") (mapcar 'add_list jack-list) (end_list)
      (start_list "s_start_mode") (mapcar 'add_list '("사용자 클릭 위치" "세그먼트 중점 시작 (1개 배치)" "간격 중심 시작 (양쪽 배치)")) (end_list)

      (defun update-ui-strut (shape-idx-str / shape-str cur-mats cur-secs)
        (setq shape-str (nth (atoi shape-idx-str) shape-list-strut))
        (if (wcmatch shape-str "H형강") 
          (setq cur-mats mat-list-h cur-secs sec-list-h) 
          (setq cur-mats mat-list-pipe cur-secs sec-list-pipe)
        )
        (start_list "s_mat") (mapcar 'add_list cur-mats) (end_list) (set_tile "s_mat" "0")
        (start_list "s_sec") (mapcar 'add_list cur-secs) (end_list)
        (if (and (wcmatch shape-str "H형강") default-h-idx)
          (set_tile "s_sec" (itoa default-h-idx))
          (set_tile "s_sec" "0")
        )
      )

      (if existing-data
        (progn
          (setq user-forced-strut-sec T) ;; 기존 데이터를 불러올 땐 2H 자동 전환을 일시 중단함
          (set_tile "s_name" (cadr existing-data))
          (setq init-shape (caddr existing-data))
          (setq shape-idx (vl-position init-shape shape-list-strut))
          (if shape-idx
            (progn (set_tile "s_shape" (itoa shape-idx)) (update-ui-strut (itoa shape-idx)))
            (progn (set_tile "s_shape" "0") (update-ui-strut "0"))
          )
          (set_tile "s_depth" (rtos (cadddr existing-data) 2 2))
          
          ;; 재질(Material) 복원
          (setq saved-mat (nth 5 existing-data))
          (setq mat-list-to-search (if (wcmatch init-shape "H형강") mat-list-h mat-list-pipe))
          (setq mat-idx (vl-position saved-mat mat-list-to-search))
          (if mat-idx (set_tile "s_mat" (itoa mat-idx)))
          
          ;; 규격(Section) 복원
          (setq saved-sec (nth 6 existing-data)) 
          (setq sec-list-to-search (if (wcmatch init-shape "H형강") sec-list-h sec-list-pipe)) 
          (setq sec-idx (vl-position saved-sec sec-list-to-search))
          (if sec-idx (set_tile "s_sec" (itoa sec-idx)))
          
          ;; 잭(Jack) 복원
          (setq saved-jack (nth 7 existing-data)) 
          (setq jack-idx (vl-position saved-jack jack-list))
          (if jack-idx 
            (set_tile "s_jack" (itoa jack-idx)) 
            (progn 
              (setq def-jack (vl-position "스크류잭" jack-list))
              (if def-jack (set_tile "s_jack" (itoa def-jack)) (set_tile "s_jack" "0"))
            )
          )
          
          (setq manual-pts (if (> (length existing-data) 8) (nth 8 existing-data) nil))
          (set_tile "s_start_mode" (if (> (length existing-data) 9) (nth 9 existing-data) "1"))
          (set_tile "s_ctc" (if (> (length existing-data) 10) (nth 10 existing-data) "5.0"))
          
          ;; [안전장치] 버팀보용 보강재 및 중간말뚝 옵션 복원 (데이터가 없으면 기본값)
          (setq strut-brace-data (if (> (length existing-data) 11) (nth 11 existing-data) nil))
          (set_tile "s_chk_stiffener_enable" (if strut-brace-data (nth 0 strut-brace-data) "1"))
          (set_tile "s_slenderness_limit" (if strut-brace-data (nth 1 strut-brace-data) "0"))
          (set_tile "s_chk_manual_interval" (if strut-brace-data (nth 2 strut-brace-data) "0"))
          
          ;; 작도가 일어난 적이 있을 때만 값을 채우고, 아니면 빈칸 유지
          (set_tile "s_manual_interval" (if (and strut-brace-data (/= (nth 3 strut-brace-data) "0.0") (/= (nth 3 strut-brace-data) ""))
                                          (nth 3 strut-brace-data)
                                          (if (and *tsp-last-strut-len* *tsp-last-calc-interval* (numberp *tsp-last-calc-interval*)) (rtos *tsp-last-calc-interval* 2 3) "")))
          (set_tile "s_stiffener_margin" (if strut-brace-data (nth 4 strut-brace-data) "50"))
          (set_tile "s_chk_post_enable" (if strut-brace-data (nth 5 strut-brace-data) "1"))
          (if (and strut-brace-data (= (nth 8 strut-brace-data) "R")) (set_tile "s_post_side_R" "1") (set_tile "s_post_side_L" "1"))
        )
        (progn
          ;; 신규 생성 시 기본값 세팅
          (set_tile "s_name" default-name)
          (set_tile "s_shape" "0")
          (setq def-jack (vl-position "스크류잭" jack-list))
          (if def-jack (set_tile "s_jack" (itoa def-jack)) (set_tile "s_jack" "1"))
          (set_tile "s_start_mode" "1")
          (set_tile "s_ctc" "5.0")
          (update-ui-strut "0")
          (setq manual-pts nil)

          ;; [초기화] 보강재 및 중간말뚝 옵션
          (set_tile "s_chk_stiffener_enable" "1")
          (set_tile "s_slenderness_limit" "0")
          (set_tile "s_chk_manual_interval" "0")
          (set_tile "s_manual_interval" (if (and *tsp-last-strut-len* *tsp-last-calc-interval* (numberp *tsp-last-calc-interval*)) (rtos *tsp-last-calc-interval* 2 3) ""))
          (set_tile "s_stiffener_margin" "50")
          (set_tile "s_chk_post_enable" "1")
          (set_tile "s_post_side_L" "1")
        )
      )
      
      ;; 팝업 리스트 데이터 추가
      (start_list "s_slenderness_limit")
      (mapcar 'add_list '("100 (표준 기준)" "120 (최대 예외 한계)"))
      (end_list)

      ;; 실시간 N등분 및 간격 계산 갱신 함수용 스팬 추정
      (setq current-strut-span 
        (cond
          ((and (boundp '*tsp-last-strut-len*) (numberp *tsp-last-strut-len*) (> *tsp-last-strut-len* 0.0)) *tsp-last-strut-len*)
          ((and (boundp '*current-segment-span*) (numberp *current-segment-span*)) *current-segment-span*)
          (t 20000.0)
        )
      )

      (defun update-strut-calc-info ()
        (vl-catch-all-apply (function (lambda ( / cur-shape cur-sec clean-sec cur-vals limit-type l-max l-max-res span-m num-div auto-interval sec-idx is-1h new-sec-str new-idx )
          (setq cur-shape (nth (atoi (get_tile "s_shape")) shape-list-strut))
          (setq sec-idx (atoi (get_tile "s_sec")))
          (if (wcmatch cur-shape "H형강")
            (setq cur-sec (nth sec-idx sec-list-h))
            (setq cur-sec (nth sec-idx sec-list-pipe))
          )
          
          ;; 1H, 2H 무관하게 한계길이는 항상 1H 베이스로 계산되도록 치환
          (setq clean-sec (if cur-sec cur-sec ""))
          (setq is-1h (if cur-sec (wcmatch cur-sec "H *") nil))
          (if (and cur-sec (wcmatch cur-sec "2H *")) (setq clean-sec (vl-string-subst "H " "2H " cur-sec)))
          
          (setq cur-vals (parse-h-spec clean-sec))
          (setq limit-type (get_tile "s_slenderness_limit"))

          (if cur-vals
            (progn
              (setq l-max-res (vl-catch-all-apply 'tsp-calc-unsupported-length (list cur-vals (if (= limit-type "0") 100.0 120.0))))
              (if (vl-catch-all-error-p l-max-res) (setq l-max 5.0) (setq l-max l-max-res))
            )
            (setq l-max 5.0)
          )
          (if (or (null l-max) (<= l-max 0.1)) (setq l-max 5.0))
          (setq span-m (/ current-strut-span 1000.0))

          ;; [2H 자동 상향] 한계길이를 넘었고, 현재 사용자가 1H를 직접 클릭하지 않았다면 2H로 자동 넘김
          (if (and (not user-forced-strut-sec) is-1h (> span-m l-max) (wcmatch cur-shape "H형강"))
            (progn
              (setq new-sec-str (vl-string-subst "2H " "H " cur-sec))
              (setq new-idx (vl-position new-sec-str sec-list-h))
              (if new-idx
                (progn (set_tile "s_sec" (itoa new-idx)) (setq cur-sec new-sec-str))
              )
            )
          )

          ;; 보강재 간격 축소 로직
          (setq num-div (fix (+ (/ span-m l-max) 0.9999)))
          (if (< num-div 1) (setq num-div 1))
          (setq auto-interval (/ span-m num-div))

          (set_tile "s_stiffener_info" (strcat "최대길이: " (rtos span-m 2 1) "m | 허용(1H): " (rtos l-max 2 2) "m | " (itoa num-div) "등분 | 간격: " (rtos auto-interval 2 3) "m" (if (and (wcmatch cur-shape "H형강") (> span-m 50.0)) "  [! 자중좌굴 50m 초과]" "")))
          
          ;; 작도를 통해 실제 길이가 확정된 상태에서만 입력칸 동기화
          (if (and (/= (get_tile "s_chk_manual_interval") "1") *tsp-last-strut-len*)
            (set_tile "s_manual_interval" (rtos auto-interval 2 3))
          )
        )))
      )

      (action_tile "s_shape" "(progn (update-ui-strut $value) (setq user-forced-strut-sec nil) (update-strut-calc-info))")
      (action_tile "s_sec" "(progn (setq user-forced-strut-sec T) (update-strut-calc-info))")
      (action_tile "s_slenderness_limit" "(progn (setq user-forced-strut-sec nil) (update-strut-calc-info))")
      (action_tile "s_manual_interval" "(set_tile \"s_chk_manual_interval\" \"1\")")
      (action_tile "s_chk_manual_interval" "(if (= $value \"0\") (update-strut-calc-info))")
      
      ;; 다이얼로그 최초 기동 시 즉시 실행
      (update-strut-calc-info)
        
      (defun get-current-brace-opt ()
        (list (get_tile "s_chk_stiffener_enable")
              (get_tile "s_slenderness_limit")
              (get_tile "s_chk_manual_interval")
              (get_tile "s_manual_interval")
              (get_tile "s_stiffener_margin")
              (get_tile "s_chk_post_enable")
              "0"
              "0"
              (if (= (get_tile "s_post_side_R") "1") "R" "L")
        )
      )

      ;; [수정 복원] 중간말뚝 추가/삭제 수동 제어 액션 연결
      ;; 더미 리스트 대신 실시간 UI 값을 온전히 s-data에 수집하여 넘겨줌으로써 잘못된 리스트 오류 원천 방어
      (action_tile "s_btn_post_add" "(progn 
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq s-brace-opt (get-current-brace-opt))
        (setq s-data (list \"ADD_POST\" (get_tile \"s_name\") res-shape res-depth res-count res-mat res-sec (nth (atoi (get_tile \"s_jack\")) jack-list) manual-pts (get_tile \"s_start_mode\") (get_tile \"s_ctc\") s-brace-opt))
        (done_dialog 97)
      )")
      (action_tile "s_btn_post_del" "(progn 
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq s-brace-opt (get-current-brace-opt))
        (setq s-data (list \"DEL_POST\" (get_tile \"s_name\") res-shape res-depth res-count res-mat res-sec (nth (atoi (get_tile \"s_jack\")) jack-list) manual-pts (get_tile \"s_start_mode\") (get_tile \"s_ctc\") s-brace-opt))
        (done_dialog 98)
      )")
      (action_tile "s_btn_post_reset" "(progn 
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq s-brace-opt (get-current-brace-opt))
        (setq s-data (list \"RESET_POST\" (get_tile \"s_name\") res-shape res-depth res-count res-mat res-sec (nth (atoi (get_tile \"s_jack\")) jack-list) manual-pts (get_tile \"s_start_mode\") (get_tile \"s_ctc\") s-brace-opt))
        (done_dialog 99)
      )")

      (action_tile "btn_redraw_strut" "(progn 
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq s-brace-opt (get-current-brace-opt))
        (setq s-data (list \"MEASURE_SIGNAL\" (get_tile \"s_name\") res-shape res-depth res-count res-mat res-sec (nth (atoi (get_tile \"s_jack\")) jack-list) manual-pts (get_tile \"s_start_mode\") (get_tile \"s_ctc\") s-brace-opt))
        (done_dialog 6)
      )")

      (action_tile "btn_draw_strut" "(progn 
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq s-brace-opt (get-current-brace-opt))
        (if (and (wcmatch res-shape \"H형강\") (> current-strut-span 50000.0))
          (alert \"경고: 버팀보 예상 길이가 자중 좌굴 한계(50m)를 초과합니다.\\n안전성에 유의하여 작도를 진행합니다.\")
        )
        (setq s-data (list \"DRAW_SIGNAL\" (get_tile \"s_name\") res-shape res-depth res-count res-mat res-sec (nth (atoi (get_tile \"s_jack\")) jack-list) manual-pts (get_tile \"s_start_mode\") (get_tile \"s_ctc\") s-brace-opt))
        (done_dialog 4)
      )")

      (action_tile "btn_measure" "(progn 
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq s-brace-opt (get-current-brace-opt))
        (setq s-data (list \"MEASURE_SIGNAL\" (get_tile \"s_name\") res-shape res-depth res-count res-mat res-sec (nth (atoi (get_tile \"s_jack\")) jack-list) manual-pts (get_tile \"s_start_mode\") (get_tile \"s_ctc\") s-brace-opt))
        (done_dialog 6)
      )")

      (action_tile "accept" "(progn 
        (setq res-name (get_tile \"s_name\"))
        (setq res-shape (nth (atoi (get_tile \"s_shape\")) shape-list-strut)) (if (null res-shape) (setq res-shape \"H형강\"))
        (setq res-depth (atof (get_tile \"s_depth\")))
        (setq m-idx (atoi (get_tile \"s_mat\"))) (if (wcmatch res-shape \"H형강\") (setq res-mat (nth m-idx mat-list-h)) (setq res-mat (nth m-idx mat-list-pipe)))
        (setq sec-idx (atoi (get_tile \"s_sec\"))) (if (wcmatch res-shape \"H형강\") (setq res-sec (nth sec-idx sec-list-h)) (setq res-sec (nth sec-idx sec-list-pipe)))
        (if (null res-sec) (setq res-sec \"H 300x300x10/15\"))
        (setq res-count (if (wcmatch res-sec \"2H *\") 2 1))
        (setq res-jack (nth (atoi (get_tile \"s_jack\")) jack-list))
        (setq res-start-mode (get_tile \"s_start_mode\"))
        (setq res-ctc (get_tile \"s_ctc\"))
        (setq s-brace-opt (get-current-brace-opt))
        (cond
          ((or (= res-name \"\") (<= res-depth 0.0)) (alert \"이름과 설치깊이를 확인하세요.\"))
          ((<= res-depth min-depth) (alert \"설치 깊이는 이전 단계보다 깊어야 합니다!\"))
          ((<= (atof res-ctc) 0.0) (alert \"배열 간격(C.T.C)은 0보다 커야 합니다.\"))
          (t
           (setq s-data (list \"버팀보(Strut)\" res-name res-shape res-depth res-count res-mat res-sec res-jack manual-pts res-start-mode res-ctc s-brace-opt))
           (done_dialog 1)
          )
        )
      )")
      (action_tile "cancel" "(done_dialog 0)")
      (setq dlg-status (start_dialog))
    )
  )
    
  (cond
    ;; 상태 코드 6 반환 시: 자동 및 수동 버팀보 실시간 도면 측정/갱신 처리
    ((= dlg-status 6)
      (progn
        (if *tsp-is-redrawing* (progn 
            (princ "\n[알림] 이미 갱신 작업 중입니다. 잠시만 기다려주세요.") 
            (strut-input-dialog s-data (nth 1 s-data) min-depth)
          )
          (progn
            (setq *tsp-is-redrawing* T)
            
            ;; [에러 트랩 추가] 에러 발생 시 *tsp-is-redrawing* 플래그를 강제 해제하여 무한 대기 방지
            (setq old-err *error*)
            (defun *error* (msg)
              (setq *tsp-is-redrawing* nil)
              (princ (strcat "\n[TSP 시스템 에러 복구] 갱신 중 문제가 발생했습니다: " msg))
              (if old-err (setq *error* old-err))
              (princ)
            )

            (princ "\n[DEBUG] 01. 상태코드 6 진입")
            (tsp-log ">>> [DCL] 상태코드 6 진입 시작")
            
            (setq s-brace-opt (nth 11 s-data))
            (if (= (type s-brace-opt) 'STR)
              (progn
                (tsp-log ">>> [DCL] s-brace-opt 문자열 감지됨. 강제 리스트 복원 수행")
                (setq s-brace-opt (read s-brace-opt))
                (setq s-data (list (nth 0 s-data) (nth 1 s-data) (nth 2 s-data) (nth 3 s-data) (nth 4 s-data) (nth 5 s-data) (nth 6 s-data) (nth 7 s-data) (nth 8 s-data) (nth 9 s-data) (nth 10 s-data) s-brace-opt))
              )
            )
            
            (princ "\n[DEBUG] 02. 전역 리스트 교체 준비")
            (setq tmp-strut-data (cons "버팀보(Strut)" (cdr s-data)))
            (setq orig-support-list *tsp-support-list*)
            (setq replaced nil new-list '())
            (foreach item *tsp-support-list*
              (if (and (= (car item) "버팀보(Strut)") (= (nth 1 item) (nth 1 tmp-strut-data)))
                (progn (setq new-list (append new-list (list tmp-strut-data))) (setq replaced T))
                (setq new-list (append new-list (list item)))
              )
            )
            (if (not replaced) (setq new-list (append new-list (list tmp-strut-data))))
            (setq *tsp-support-list* new-list)
            
            (if (and (boundp '*tsp-current-seg-idx*) *tsp-current-seg-idx*)
              (progn
                (setq cur-seg (nth *tsp-current-seg-idx* *segment-list*))
                (setq cur-supp-list (cdr (assoc 'SUPPORT-LIST cur-seg)))
                (setq tmp-replaced nil tmp-new-supp '())
                (foreach item cur-supp-list
                  (if (and (wcmatch (car item) "버팀보*") (= (nth 1 item) (nth 1 tmp-strut-data)))
                    (progn (setq tmp-new-supp (append tmp-new-supp (list tmp-strut-data))) (setq tmp-replaced T))
                    (setq tmp-new-supp (append tmp-new-supp (list item)))
                  )
                )
                (if (not tmp-replaced) (setq tmp-new-supp (append tmp-new-supp (list tmp-strut-data))))
                (setq *segment-list*
                  (subst (subst (cons 'SUPPORT-LIST tmp-new-supp) (assoc 'SUPPORT-LIST cur-seg) cur-seg) cur-seg *segment-list*))
              )
            )

            (princ "\n[DEBUG] 03. 실시간 평면 갱신 (자동 작도분)")
            (tsp-log ">>> [Main] tsp-redraw-realtime-plan 호출 검토")
            (if (and (boundp '*tsp-boundary-ent*) *tsp-boundary-ent* (boundp '*tsp-boundary-orient*) *tsp-boundary-orient*)
              (progn
                (tsp-log (strcat ">>> [Main] 경계선 데이터 유효 확인 완료. 핸들: " (if (entget *tsp-boundary-ent*) (cdr (assoc 5 (entget *tsp-boundary-ent*))) "엔티티사망")))
                (tsp-redraw-realtime-plan *tsp-boundary-ent* *tsp-boundary-orient*)
                (tsp-log ">>> [Main] tsp-redraw-realtime-plan 실행 무사 완료")
              )
              (tsp-log ">>> [경고] *tsp-boundary-ent* 전역 변수가 비어있어 재작도를 건너뜁니다!")
            )

            (princ "\n[DEBUG] 04. 수동 작도 객체 검색 시작")
            (setq unique-params '())
            (foreach e manual-drawn-ents
              (if (and e (entget e '("TSP_STRUT_SPEC")))
                (progn
                  (setq xdata (cdadr (assoc -3 (entget e '("TSP_STRUT_SPEC")))))
                  (if xdata
                    (if (and (> (length xdata) 7) (= (cdr (nth 7 xdata)) "MANUAL_STRUT"))
                      (progn
                        (setq seg-id (cdr (nth 0 xdata)))
                        (setq pt1 (cdr (nth 2 xdata)))
                        (setq pt2 (cdr (nth 3 xdata)))
                        (setq p-pair (list pt1 pt2 seg-id))
                        (if (not (vl-member-if '(lambda (x) (and (equal pt1 (car x) 1e-4) (equal pt2 (cadr x) 1e-4))) unique-params))
                          (setq unique-params (append unique-params (list p-pair)))
                        )
                      )
                    )
                  )
                )
              )
            )

            (princ "\n[DEBUG] 05. 기존 수동 작도 객체 삭제 시작")
            (if unique-params
              (progn
                (foreach e manual-drawn-ents 
                  (if (entget e) 
                    (progn
                      (vl-catch-all-apply 'entmod (list (list (cons -1 e) (list -3 (list "TSP_STRUT_SPEC")))))
                      (vl-catch-all-apply 'entmod (list (list (cons -1 e) (list -3 (list "TSP_LISP_BRACE")))))
                      (tsp-safe-hide-ent e)  ;; 물리 삭제 대신 ARX가 지우도록 안전 숨김 처리
                    )
                  )
                )
                (setq manual-drawn-ents '())
                (setq res-sec (nth 6 s-data) jack-type (nth 7 s-data) is-double (if (>= (nth 4 s-data) 2) T nil) s-brace-opt (nth 11 s-data))
                
                (princ "\n[DEBUG] 06. 새로운 수동 작도(버팀보) 시작")
                (foreach param unique-params
                  (setq pt1 (car param) pt2 (cadr param) seg-id (caddr param))
                  (setq array-brace-opt s-brace-opt)
                  (if array-brace-opt (setq array-brace-opt (cons "0" (cdr array-brace-opt))))
                  (setq new-ents (tsp-draw-manual-strut pt1 pt2 res-sec jack-type is-double array-brace-opt seg-id))
                  (setq manual-drawn-ents (append manual-drawn-ents new-ents))
                )
                
                (princ "\n[DEBUG] 07. 새로운 수동 작도(보강재) 시작")
                (setq all-pts (mapcar 'car unique-params))
                (if (and s-brace-opt (= (nth 0 s-brace-opt) "1") (> (length all-pts) 0))
                  (progn
                    (setq pt1 (car (car unique-params)) pt2 (cadr (car unique-params)) target-seg-id (caddr (car unique-params)))
                    (setq strut-ang (angle pt1 pt2) strut-len (distance pt1 pt2))
                    (if (boundp 'tsp-draw-realtime-continuous-braces)
                      (progn
                        (setq temp-brace-ents (tsp-draw-realtime-continuous-braces all-pts s-brace-opt res-sec is-double strut-ang strut-len target-seg-id))
                        (setq manual-drawn-ents (append manual-drawn-ents temp-brace-ents))
                      )
                    )
                  )
                )
              ) ;; unique-params의 progn을 여기서 미리 닫습니다.
            ) ;; unique-params의 if를 여기서 미리 닫습니다.

            (princ "\n[DEBUG] 08. 재생성(REGEN) 및 버퍼 초기화 실행")
            (vl-catch-all-apply 'vla-regen (list (vla-get-activedocument (vlax-get-acad-object)) 1))
            
            ;; [디버깅 프롬프트 추가] 문제의 원인을 파악하기 위해 단계별 촘촘한 로그 기록
            (princ "\n[DEBUG-FLOW] 08-1. Alert 팝업창 호출 직전")
            (alert "도면 갱신이 완료되었습니다.\n[확인]을 누르면 도면 측정/확인 모드로 진입합니다.")
            (princ "\n[DEBUG-FLOW] 08-2. Alert 팝업창 닫힘 (사용자 확인 누름)")

            (princ "\n[DEBUG-FLOW] 09. ARX 도면제어 함수 호출 직전!")
            ;; ARX 함수가 메모리에 정상적으로 바인딩되어 있는지 먼저 확인합니다.
            (princ (strcat "\n[DEBUG-FLOW] 09-1. tsp-pause-for-measurement 타입 확인: " (vl-princ-to-string (type tsp-pause-for-measurement))))

            (if tsp-pause-for-measurement
              (progn
                (princ "\n[DEBUG-FLOW] 09-2. tsp-pause-for-measurement 내부 진입 시도...")
                ;; 에러 발생 시 캐치하기 위해 vl-catch-all-apply로 래핑하여 실행합니다.
                (setq debug-arx-result (vl-catch-all-apply 'tsp-pause-for-measurement))
                
                (if (vl-catch-all-error-p debug-arx-result)
                  (princ (strcat "\n[DEBUG-ERROR] ARX 함수 내부에서 크래시 발생!: " (vl-catch-all-error-message debug-arx-result)))
                  (princ (strcat "\n[DEBUG-FLOW] 10. ARX 도면제어 함수 무사 종료됨. 반환값: " (vl-princ-to-string debug-arx-result)))
                )
                (tsp-log ">>> [Main] ARX 도면제어 무사 종료됨")
              )
              (progn
                (princ "\n[DEBUG-ERROR] TSP - 도면 제어 모듈(ARX)을 찾을 수 없습니다!")
                (alert "TSP - 도면 제어 모듈이 로드되지 않았습니다.")
              )
            )
            
            (princ "\n[DEBUG-FLOW] 11. DCL 다이얼로그 재호출 직전 (여기까지 딜레이 없이 한 번에 도달했다면 스킵된 것임)")
            (setq *tsp-support-list* orig-support-list)
            
            ;; [복원] 정상 작동 시 에러 트랩 복구 및 플래그 해제
            (setq *error* old-err) 
            (setq *tsp-is-redrawing* nil)
            
            (strut-input-dialog s-data (nth 1 s-data) min-depth)
          )
        )
      )
    )
    
    ((= dlg-status 5)
      (progn
        (setq unique-params '())
        (foreach e manual-drawn-ents
          (if (and e (entget e '("TSP_STRUT_SPEC")))
            (progn
              (setq xdata (cdadr (assoc -3 (entget e '("TSP_STRUT_SPEC")))))
              (if xdata
                (if (and (> (length xdata) 7) (= (cdr (nth 7 xdata)) "MANUAL_STRUT"))
                  (progn
                    (setq seg-id (cdr (nth 0 xdata)))
                    (setq pt1 (cdr (nth 2 xdata)))
                    (setq pt2 (cdr (nth 3 xdata)))
                    (setq p-pair (list pt1 pt2 seg-id))
                    (if (not (vl-member-if '(lambda (x) (and (equal pt1 (car x) 1e-4) (equal pt2 (cadr x) 1e-4))) unique-params))
                      (setq unique-params (append unique-params (list p-pair)))
                    )
                  )
                )
              )
            )
          )
        )
        (if unique-params
          (progn
            (foreach e manual-drawn-ents (if (entget e) (tsp-safe-hide-ent e)))
            (setq manual-drawn-ents '())
            
            ;; [안전장치 추가] s-brace-opt 문자열 리스트 변환 방어코드 추가 (잘못된 리스트 오류 차단)
            (setq s-brace-opt (nth 11 s-data))
            (if (= (type s-brace-opt) 'STR)
              (progn
                (setq s-brace-opt (read s-brace-opt))
                (setq s-data (list (nth 0 s-data) (nth 1 s-data) (nth 2 s-data) (nth 3 s-data) (nth 4 s-data) (nth 5 s-data) (nth 6 s-data) (nth 7 s-data) (nth 8 s-data) (nth 9 s-data) (nth 10 s-data) s-brace-opt))
              )
            )
            
            (setq res-sec (nth 6 s-data) jack-type (nth 7 s-data) is-double (if (>= (nth 4 s-data) 2) T nil) s-brace-opt (nth 11 s-data))
            (foreach param unique-params
              (setq pt1 (car param) pt2 (cadr param) seg-id (caddr param))
              (setq array-brace-opt s-brace-opt)
              (if array-brace-opt (setq array-brace-opt (cons "0" (cdr array-brace-opt))))
              (setq new-ents (tsp-draw-manual-strut pt1 pt2 res-sec jack-type is-double array-brace-opt seg-id))
              (setq manual-drawn-ents (append manual-drawn-ents new-ents))
            )
            (setq all-pts (mapcar 'car unique-params))
            (if (and s-brace-opt (= (nth 0 s-brace-opt) "1") (> (length all-pts) 0))
              (progn
                (setq pt1 (car (car unique-params)) pt2 (cadr (car unique-params)) target-seg-id (caddr (car unique-params)))
                (setq strut-ang (angle pt1 pt2) strut-len (distance pt1 pt2))
                (if (boundp 'tsp-draw-realtime-continuous-braces)
                  (progn
                    (setq temp-brace-ents (tsp-draw-realtime-continuous-braces all-pts s-brace-opt res-sec is-double strut-ang strut-len target-seg-id))
                    (setq manual-drawn-ents (append manual-drawn-ents temp-brace-ents))
                 )
            )
          )
        )
        ;; [크래시 해결] command 대신 ActiveX 방식의 재생성(vla-regen) 사용
        (vl-catch-all-apply 'vla-regen (list (vla-get-activedocument (vlax-get-acad-object)) 1))
        (princ "\n[성공] 도면의 버팀보 보강재 설정이 갱신되었습니다.")
      )
          (alert "갱신할 객체가 없습니다. 먼저 '도면에서 직접 작도'로 버팀보를 배치하세요.")
        )
        (strut-input-dialog s-data (nth 1 s-data) min-depth)
      )
    )
    
    ((= dlg-status 4) s-data)
    ((= dlg-status 1) s-data)
    
    ;; ------------------ 제어 명령 수동 추가 분기점 ------------------
    ((= dlg-status 97)
      (progn
        ;; [크래시 해결] command DELAY 완전 삭제
        (setq snap-added-posts  (vlax-ldata-get "TSP_DICT" "ADDED_POSTS"))
        (setq snap-deleted-posts (vlax-ldata-get "TSP_DICT" "DELETED_POSTS"))
        (setq orig-support-list *tsp-support-list*)
        (setq orig-segment-list *segment-list*)
        
        (setq tmp-target-id
          (if (and (boundp '*tsp-current-seg-idx*) *tsp-current-seg-idx*
                   (boundp '*segment-list*) *segment-list*)
            (progn
              (setq cur-seg (nth *tsp-current-seg-idx* *segment-list*))
              (if (assoc 'ID cur-seg) (cdr (assoc 'ID cur-seg)) 0)
            )
            0
          )
        )
        (if manual-drawn-ents
          (progn
            ;; [안전성 수정] s-brace-opt가 문자열 상태일 때의 강제 복원 장치 적용
            (setq s-brace-opt (nth 11 s-data))
            (if (= (type s-brace-opt) 'STR) (setq s-brace-opt (read s-brace-opt)))
            
            ;; [치명적 버그 수정] 기존의 비어있는 existing-data 대신 모든 UI 정보가 확보된 s-data를 활용하여 원소 누락 리스트 에러 원천 차단
            (setq tmp-strut-data (cons "버팀보(Strut)" (cdr s-data)))
            
            (setq replaced nil new-list '())
            (foreach item *tsp-support-list*
              (if (and (= (car item) "버팀보(Strut)") (= (nth 1 item) (nth 1 tmp-strut-data)))
                (progn (setq new-list (append new-list (list tmp-strut-data))) (setq replaced T))
                (setq new-list (append new-list (list item)))
              )
            )
            (if (not replaced) (setq new-list (append new-list (list tmp-strut-data))))
            (setq *tsp-support-list* new-list)
            
            (if (and (boundp '*tsp-current-seg-idx*) *tsp-current-seg-idx*)
              (progn
                (setq cur-seg (nth *tsp-current-seg-idx* *segment-list*))
                (setq cur-supp-list (cdr (assoc 'SUPPORT-LIST cur-seg)))
                (setq tmp-replaced nil tmp-new-supp '())
                (foreach item cur-supp-list
                  (if (and (wcmatch (car item) "버팀보*") (= (nth 1 item) (nth 1 tmp-strut-data)))
                    (progn (setq tmp-new-supp (append tmp-new-supp (list tmp-strut-data))) (setq tmp-replaced T))
                    (setq tmp-new-supp (append tmp-new-supp (list item)))
                  )
                )
                (if (not tmp-replaced) (setq tmp-new-supp (append tmp-new-supp (list tmp-strut-data))))
                (setq *segment-list*
                  (subst (subst (cons 'SUPPORT-LIST tmp-new-supp) (assoc 'SUPPORT-LIST cur-seg) cur-seg) cur-seg *segment-list*))
              )
            )
          )
        )
        (if (boundp 'tsp-manual-add-post) (tsp-manual-add-post tmp-target-id))
        (if (and (boundp '*tsp-boundary-ent*) *tsp-boundary-ent*
                 (boundp '*tsp-boundary-orient*) *tsp-boundary-orient*)
          (tsp-redraw-realtime-plan *tsp-boundary-ent* *tsp-boundary-orient*)
        )
        (setq *tsp-support-list* orig-support-list)
        (setq *segment-list* orig-segment-list)
        (setq dlg-result-97 (strut-input-dialog existing-data (nth 1 existing-data) min-depth))
        (if (not dlg-result-97)
          (progn
            (vlax-ldata-put "TSP_DICT" "ADDED_POSTS" snap-added-posts)
            (vlax-ldata-put "TSP_DICT" "DELETED_POSTS" snap-deleted-posts)
          )
        )
        dlg-result-97
      )
    )
    
    ;; ------------------ 제어 명령 수동 삭제 분기점 ------------------
    ((= dlg-status 98)
      (progn
        ;; [크래시 해결] command DELAY 완전 삭제
        (setq orig-support-list *tsp-support-list*)
        (setq orig-segment-list *segment-list*)
        (setq tmp-target-id
          (if (and (boundp '*tsp-current-seg-idx*) *tsp-current-seg-idx*
                   (boundp '*segment-list*) *segment-list*)
            (progn
              (setq cur-seg (nth *tsp-current-seg-idx* *segment-list*))
              (if (assoc 'ID cur-seg) (cdr (assoc 'ID cur-seg)) 0)
            )
            0
          )
        )
        (if manual-drawn-ents
          (progn
            ;; [안전성 수정] 방어코드 및 s-data 기반 리스트 동기화 적용
            (setq s-brace-opt (nth 11 s-data))
            (if (= (type s-brace-opt) 'STR) (setq s-brace-opt (read s-brace-opt)))
            (setq tmp-strut-data (cons "버팀보(Strut)" (cdr s-data)))
            
            (setq replaced nil new-list '())
            (foreach item *tsp-support-list*
              (if (and (= (car item) "버팀보(Strut)") (= (nth 1 item) (nth 1 tmp-strut-data)))
                (progn (setq new-list (append new-list (list tmp-strut-data))) (setq replaced T))
                (setq new-list (append new-list (list item)))
              )
            )
            (if (not replaced) (setq new-list (append new-list (list tmp-strut-data))))
            (setq *tsp-support-list* new-list)
            
            (if (and (boundp '*tsp-current-seg-idx*) *tsp-current-seg-idx*)
              (progn
                (setq cur-seg (nth *tsp-current-seg-idx* *segment-list*))
                (setq cur-supp-list (cdr (assoc 'SUPPORT-LIST cur-seg)))
                (setq tmp-replaced nil tmp-new-supp '())
                (foreach item cur-supp-list
                  (if (and (wcmatch (car item) "버팀보*") (= (nth 1 item) (nth 1 tmp-strut-data)))
                    (progn (setq tmp-new-supp (append tmp-new-supp (list tmp-strut-data))) (setq tmp-replaced T))
                    (setq tmp-new-supp (append tmp-new-supp (list item)))
                  )
                )
                (if (not tmp-replaced) (setq tmp-new-supp (append tmp-new-supp (list tmp-strut-data))))
                (setq *segment-list*
                  (subst (subst (cons 'SUPPORT-LIST tmp-new-supp) (assoc 'SUPPORT-LIST cur-seg) cur-seg) cur-seg *segment-list*))
              )
            )
          )
        )
        (if (boundp 'tsp-manual-delete-post) (tsp-manual-delete-post tmp-target-id))
        (if (and (boundp '*tsp-boundary-ent*) *tsp-boundary-ent*
                 (boundp '*tsp-boundary-orient*) *tsp-boundary-orient*)
          (tsp-redraw-realtime-plan *tsp-boundary-ent* *tsp-boundary-orient*)
        )
        (setq *tsp-support-list* orig-support-list)
        (setq *segment-list* orig-segment-list)
        (strut-input-dialog existing-data (nth 1 existing-data) min-depth)
      )
    )
    
    ;; ------------------ 제어 명령 수동 초기화 분기점 ------------------
    ((= dlg-status 99)
      (progn
        ;; [크래시 해결] command DELAY 완전 삭제
        (setq orig-support-list *tsp-support-list*)
        (setq orig-segment-list *segment-list*)
        (setq tmp-target-id
          (if (and (boundp '*tsp-current-seg-idx*) *tsp-current-seg-idx*
                   (boundp '*segment-list*) *segment-list*)
            (progn
              (setq cur-seg (nth *tsp-current-seg-idx* *segment-list*))
              (if (assoc 'ID cur-seg) (cdr (assoc 'ID cur-seg)) 0)
            )
            0
          )
        )
        (if manual-drawn-ents
          (progn
            ;; [안전성 수정] 방어코드 및 s-data 기반 리스트 동기화 적용
            (setq s-brace-opt (nth 11 s-data))
            (if (= (type s-brace-opt) 'STR) (setq s-brace-opt (read s-brace-opt)))
            (setq tmp-strut-data (cons "버팀보(Strut)" (cdr s-data)))
            
            (setq replaced nil new-list '())
            (foreach item *tsp-support-list*
              (if (and (= (car item) "버팀보(Strut)") (= (nth 1 item) (nth 1 tmp-strut-data)))
                (progn (setq new-list (append new-list (list tmp-strut-data))) (setq replaced T))
                (setq new-list (append new-list (list item)))
              )
            )
            (if (not replaced) (setq new-list (append new-list (list tmp-strut-data))))
            (setq *tsp-support-list* new-list)
            
            (if (and (boundp '*tsp-current-seg-idx*) *tsp-current-seg-idx*)
              (progn
                (setq cur-seg (nth *tsp-current-seg-idx* *segment-list*))
                (setq cur-supp-list (cdr (assoc 'SUPPORT-LIST cur-seg)))
                (setq tmp-replaced nil tmp-new-supp '())
                (foreach item cur-supp-list
                  (if (and (wcmatch (car item) "버팀보*") (= (nth 1 item) (nth 1 tmp-strut-data)))
                    (progn (setq tmp-new-supp (append tmp-new-supp (list tmp-strut-data))) (setq tmp-replaced T))
                    (setq tmp-new-supp (append tmp-new-supp (list item)))
                  )
                )
                (if (not tmp-replaced) (setq tmp-new-supp (append tmp-new-supp (list tmp-strut-data))))
                (setq *segment-list*
                  (subst (subst (cons 'SUPPORT-LIST tmp-new-supp) (assoc 'SUPPORT-LIST cur-seg) cur-seg) cur-seg *segment-list*))
              )
            )
          )
        )
        (if (boundp 'tsp-delete-manual-post-by-segment)
          (progn
            (tsp-delete-manual-post-by-segment tmp-target-id)
            (princ (strcat "\n[초기화] Seg-" (itoa tmp-target-id) " 구역의 수동 중간말뚝이 초기화되었습니다."))
          )
        )
        (if (and (boundp '*tsp-boundary-ent*) *tsp-boundary-ent*
                 (boundp '*tsp-boundary-orient*) *tsp-boundary-orient*)
          (tsp-redraw-realtime-plan *tsp-boundary-ent* *tsp-boundary-orient*)
        )
        (setq *tsp-support-list* orig-support-list)
        (setq *segment-list* orig-segment-list)
        (strut-input-dialog existing-data (nth 1 existing-data) min-depth)
      )
    )
    (t nil)
  )
)

;;;;==========================================================================
;;;; defun anchor-input-dialog : 앵커 입력창
;;;;==========================================================================
  (defun anchor-input-dialog (existing-data default-name min-depth / a-result a-data mat-list-anchor sec-list-anchor res-name res-shape res-depth res-ang res-free res-bond res-mat res-sec init-shape shape-idx i)
    (setq mat-list-anchor '("SWPC7A" "SWPC7B")) (setq sec-list-anchor '()) (setq i 1)
    (repeat 15 (setq sec-list-anchor (append sec-list-anchor (list (strcat "Strand12.7x" (itoa i) "EA")))) (setq i (1+ i)))
    (if (new_dialog "tsp_support_anchor" dcl-id)
      (progn
        (start_list "a_shape") (mapcar 'add_list shape-list-anchor) (end_list)
        (start_list "a_mat") (mapcar 'add_list mat-list-anchor) (end_list)
        (start_list "a_sec") (mapcar 'add_list sec-list-anchor) (end_list)
        (if existing-data
          (progn
            (set_tile "a_name" (cadr existing-data))
            (setq init-shape (caddr existing-data)) (setq shape-idx (vl-position init-shape shape-list-anchor))
            (if shape-idx (set_tile "a_shape" (itoa shape-idx)) (set_tile "a_shape" "0"))
            (set_tile "a_depth" (rtos (cadddr existing-data) 2 2)) (set_tile "a_angle" (rtos (nth 4 existing-data) 2 1)) (set_tile "a_free" (rtos (nth 5 existing-data) 2 2)) (set_tile "a_bond" (rtos (nth 6 existing-data) 2 2))
            (set_tile "a_mat" "0") (set_tile "a_sec" "0")
          )
          (progn (set_tile "a_name" default-name) (set_tile "a_shape" "0") (set_tile "a_angle" "30") (set_tile "a_bond" "3") (set_tile "a_mat" "1") (set_tile "a_sec" "3"))
        )
        (action_tile "accept" "(progn (setq res-name (get_tile \"a_name\")) (setq res-shape (nth (atoi (get_tile \"a_shape\")) shape-list-anchor)) (setq res-depth (atof (get_tile \"a_depth\"))) (setq res-ang (atof (get_tile \"a_angle\"))) (setq res-free (atof (get_tile \"a_free\"))) (setq res-bond (atof (get_tile \"a_bond\"))) (setq res-mat (nth (atoi (get_tile \"a_mat\")) mat-list-anchor)) (setq res-sec (nth (atoi (get_tile \"a_sec\")) sec-list-anchor)) (cond ((or (= res-name \"\") (<= res-depth 0.0)) (alert \"이름과 설치깊이를 확인하세요.\")) ((< res-free 4.5) (alert \"자유장은 최소 4.5m 이상이어야 합니다.\")) ((> res-ang 40.0) (alert \"설치각도는 40도 이하여야 합니다.\")) ((<= res-depth min-depth) (alert \"설치 깊이는 이전 단계보다 깊어야 합니다!\")) (t (setq a-data (list \"앵커(Earth Anchor)\" res-name res-shape res-depth res-ang res-free res-bond res-mat res-sec)) (done_dialog 1))))")
        (action_tile "cancel" "(done_dialog 0)") (if (= (start_dialog) 1) a-data nil)
      )
    )
  )

;;;;==========================================================================
;;;; defun update-support-list : 지보재 리스트를 DCL에 출력
;;;;==========================================================================
  (defun update-support-list (/ s-type s-code disp-str free-len bond-len s-count s-spec formatted-spec)
  (start_list "support_list")
  (foreach item temp-supports
    (if (and (listp item) (> (length item) 0))
      (progn
        (setq s-type (car item))
        (cond
          ((wcmatch s-type "버팀보*") 
           (setq s-code "ST") 
           (setq s-count (nth 4 item))
           (setq s-spec (nth 6 item))
           (if (and s-count (> s-count 1))
             (if (wcmatch s-spec "2H *")
               (setq formatted-spec s-spec) 
               (setq formatted-spec (strcat (itoa s-count) s-spec)) 
             )
             (setq formatted-spec s-spec)
           )
           (setq disp-str (strcat (cadr item) "     " s-code "     " (rtos (cadddr item) 2 2) "m     " formatted-spec))
           (add_list disp-str)
          )
          ((wcmatch s-type "앵커*") 
           (setq s-code "EA") 
           (setq free-len (rtos (nth 5 item) 2 2)) 
           (setq bond-len (rtos (nth 6 item) 2 2)) 
           (setq disp-str (strcat (cadr item) "     " s-code "     " (rtos (cadddr item) 2 2) "m   (정착장 " bond-len "m 자유장 " free-len "m)"))
           (add_list disp-str)
          )
          ;; [추가/수정] 침묵하지 않고 명시적으로 오류를 표출하여 데이터 오염을 경고
          (t 
           (setq s-code "ERROR")
           (setq disp-str (strcat "!! [데이터 오류] 비정상 패킷: " (if (= (type s-type) 'STR) s-type "Unknown") " !!"))
           ;; 캐드 명령창에 디버깅용 로그 출력
           (princ (strcat "\n[경고: TSP] 지보재 리스트에 오염된 데이터가 감지되었습니다: " (vl-princ-to-string item)))
           (add_list disp-str)
          )
        )
      )
    )
  )
  (end_list)
)


  ;; ==========================================================================
  ;; 부모 대화상자(지보재 관리창) 메인 제어 루프
  ;; ==========================================================================
  (while loop-support
    (if restore-action
      (progn
        ;; 자식 창(버팀보 입력) 즉시 팝업 복원 (도면 작도 후)
        (setq min-depth 0.0)
        (if (and (= restore-type "MOD") (> restore-idx 0))
          (setq min-depth (cadddr (nth (1- restore-idx) temp-supports)))
        )
        (if (= restore-type "ADD")
           (setq min-depth (if temp-supports (cadddr (last temp-supports)) 0.0))
        )
        
        ;; 복원 데이터(restored-data)에 12번째 항목(s-brace-opt)을 정상적으로 포함시켜 상태 증발 방지
        (setq restored-data (list "RESTORE_SIGNAL"
                                  (nth 1 restore-data)
                                  (nth 2 restore-data)
                                  (nth 3 restore-data)
                                  (nth 4 restore-data)
                                  (nth 5 restore-data)
                                  (nth 6 restore-data)
                                  (nth 7 restore-data)
                                  manual-pts
                                  (nth 9 restore-data)
                                  (nth 10 restore-data)
                                  (nth 11 restore-data)))
        (setq new-data (strut-input-dialog restored-data nil min-depth))
          (cond
            ((and new-data (= (car new-data) "DRAW_SIGNAL"))
              (setq restore-data new-data)
              (setq result 4) ;; 다시 한 번 도면에 그리고 싶을 때
            )
            ((and new-data (wcmatch (car new-data) "*_POST"))
              ;; 수동 중간말뚝 제어 3중 검증 신호 전달
              (setq restore-data new-data)
              (setq tmp-id (if (assoc 'ID (nth restore-idx *segment-list*)) (cdr (assoc 'ID (nth restore-idx *segment-list*))) 0))
              ;; [버그B-2 수정] manual-drawn-ents의 버팀보를 *tsp-support-list*에 임시 반영
              (setq orig-support-list *tsp-support-list*)
              (setq orig-segment-list *segment-list*)
              (if (and manual-drawn-ents restore-data)
                (progn
                  (setq tmp-strut-data (cons "버팀보(Strut)" (cdr restore-data)))
                  ;; *tsp-support-list* 임시 반영
                  (setq replaced nil new-list '())
                  (foreach item *tsp-support-list*
                    (if (and (= (car item) "버팀보(Strut)") (= (nth 1 item) (nth 1 tmp-strut-data)))
                      (progn (setq new-list (append new-list (list tmp-strut-data))) (setq replaced T))
                      (setq new-list (append new-list (list item)))
                    )
                  )
                  (if (not replaced) (setq new-list (append new-list (list tmp-strut-data))))
                  (setq *tsp-support-list* new-list)
                  ;; [BugC-4 수정] *segment-list* 현재 세그먼트의 SUPPORT-LIST에도 임시 반영
                  (if (and (boundp '*tsp-current-seg-idx*) *tsp-current-seg-idx*)
                    (progn
                      (setq cur-seg (nth *tsp-current-seg-idx* *segment-list*))
                      (setq cur-supp-list (cdr (assoc 'SUPPORT-LIST cur-seg)))
                      (setq tmp-replaced nil tmp-new-supp '())
                      (foreach item cur-supp-list
                        (if (and (wcmatch (car item) "버팀보*") (= (nth 1 item) (nth 1 tmp-strut-data)))
                          (progn (setq tmp-new-supp (append tmp-new-supp (list tmp-strut-data))) (setq tmp-replaced T))
                          (setq tmp-new-supp (append tmp-new-supp (list item)))
                        )
                      )
                      (if (not tmp-replaced) (setq tmp-new-supp (append tmp-new-supp (list tmp-strut-data))))
                      (setq *segment-list*
                        (subst (subst (cons 'SUPPORT-LIST tmp-new-supp)
                                      (assoc 'SUPPORT-LIST cur-seg)
                                      cur-seg)
                               cur-seg *segment-list*))
                    )
                  )
                )
              )
              (if (= (car new-data) "ADD_POST") (if (boundp 'tsp-manual-add-post) (tsp-manual-add-post tmp-id) (alert "수동 추가 함수 오류")))
              (if (= (car new-data) "DEL_POST") (if (boundp 'tsp-manual-delete-post) (tsp-manual-delete-post tmp-id) (alert "수동 삭제 함수 오류")))
              (if (= (car new-data) "RESET_POST") (if (boundp 'tsp-delete-manual-post-by-segment) (tsp-delete-manual-post-by-segment tmp-id) (alert "수동 초기화 함수 오류")))
              ;; 임시 반영 해제
              (setq *tsp-support-list* orig-support-list)
              (setq *segment-list* orig-segment-list)
              (setq result 4) ;; 창 다시 열기 (DRAW_SIGNAL과 동일한 취급)
            )
            (t
              (setq restore-action nil)
              (if new-data
                (progn
                  (foreach e manual-drawn-ents (if (entget e) (vl-catch-all-apply 'entdel (list e))))
                  (if (boundp 'temp-brace-ents) (foreach e temp-brace-ents (if (entget e) (vl-catch-all-apply 'entdel (list e)))))
                  (setq manual-drawn-ents '() temp-brace-ents '())
                  
                  (if (= restore-type "ADD")
                    (setq temp-supports (append temp-supports (list new-data)))
                    (progn
                      (setq i 0 new-list '())
                      (foreach item temp-supports
                        (if (= i restore-idx)
                          (setq new-list (append new-list (list new-data)))
                          (setq new-list (append new-list (list item)))
                        )
                        (setq i (1+ i))
                      )
                      (setq temp-supports new-list)
                    )
                  )
                )
                (progn
                  (foreach e manual-drawn-ents (if (entget e) (vl-catch-all-apply 'entdel (list e))))
                  (if (boundp 'temp-brace-ents) (foreach e temp-brace-ents (if (entget e) (vl-catch-all-apply 'entdel (list e)))))
                  (setq manual-drawn-ents '() temp-brace-ents '())
                )
              )
              
              (if (and (boundp '*tsp-current-seg-idx*) *tsp-current-seg-idx*)
                (progn
                  (setq *segment-list* (subst (subst (cons 'SUPPORT-LIST temp-supports) 
                                              (assoc 'SUPPORT-LIST (nth *tsp-current-seg-idx* *segment-list*)) 
                                              (nth *tsp-current-seg-idx* *segment-list*))
                                       (nth *tsp-current-seg-idx* *segment-list*)
                                       *segment-list*))
                  (if (boundp 'tsp-redraw-realtime-plan) (tsp-redraw-realtime-plan *tsp-boundary-ent* *tsp-boundary-orient*))
                )
              )
              (command "_.REGEN")
              
              (setq result 99) ;; 자식창 취소 시 부모창으로 복귀하도록 더미값 할당
            )
        )
      )
      (progn
        ;; 정상 부모 창 오픈
        (if (new_dialog "tsp_support" dcl-id)
          (progn
            (start_list "support_type_sel") (mapcar 'add_list support-types) (end_list) (set_tile "support_type_sel" "0")
            (update-support-list)
            
            (action_tile "btn_add" "(progn 
              (setq t-idx (atoi (get_tile \"support_type_sel\"))) 
              (setq t-str (nth t-idx support-types)) 
              (setq count 1) 
              (foreach item temp-supports (if (= (car item) t-str) (setq count (1+ count)))) 
              (if (wcmatch t-str \"버팀보*\") (setq def-name (strcat \"Strut_\" (itoa count)))) 
              (if (wcmatch t-str \"앵커*\") (setq def-name (strcat \"Anchor_\" (itoa count)))) 
              (setq last-depth (if temp-supports (cadddr (last temp-supports)) 0.0)) 
              (setq new-data nil) 
              (setq manual-drawn-ents '()) ;; 새로 입력 시 찌꺼기 추적 초기화
              
              (if (wcmatch t-str \"버팀보*\") 
                (setq new-data (strut-input-dialog nil def-name last-depth)) 
                (setq new-data (anchor-input-dialog nil def-name last-depth))) 
              
              (if (and new-data (= (car new-data) \"DRAW_SIGNAL\"))
                (progn (setq restore-data new-data restore-type \"ADD\" restore-action T) (done_dialog 4))
                (if new-data (progn (setq temp-supports (append temp-supports (list new-data))) (update-support-list)))
              )
            )")
            
            (action_tile "btn_modify" "(progn 
              (setq sel-idx-str (get_tile \"support_list\")) 
              (if (and sel-idx-str (/= sel-idx-str \"\")) 
                (progn 
                  (setq sel-idx (atoi sel-idx-str)) 
                  (setq existing-item (nth sel-idx temp-supports)) 
                  (setq ex-type (car existing-item)) 
                  (setq min-depth 0.0) 
                  (if (> sel-idx 0) (setq min-depth (cadddr (nth (1- sel-idx) temp-supports)))) 
                  (setq mod-data nil) 
                  (setq manual-drawn-ents '()) ;; 수정 시 찌꺼기 추적 초기화
                  
                  (if (wcmatch ex-type \"버팀보*\") 
                    (setq mod-data (strut-input-dialog existing-item nil min-depth)) 
                    (setq mod-data (anchor-input-dialog existing-item nil min-depth))) 
                  
                  (if (and mod-data (= (car mod-data) \"DRAW_SIGNAL\"))
                    (progn (setq restore-data mod-data restore-type \"MOD\" restore-idx sel-idx restore-action T) (done_dialog 4))
                    (if mod-data 
                      (progn 
                        (setq i 0 new-list '()) 
                        (foreach item temp-supports 
                          (if (= i sel-idx) 
                            (setq new-list (append new-list (list mod-data))) 
                            (setq new-list (append new-list (list item)))) 
                          (setq i (1+ i))) 
                        (setq temp-supports new-list) 
                        (update-support-list)
                      )
                    )
                  )
                ) 
                (alert \"수정할 항목을 선택하세요!\")
              )
            )")
            
            (action_tile "btn_delete" "(progn (setq sel-idx (atoi (get_tile \"support_list\"))) (if (and temp-supports (>= sel-idx 0) (< sel-idx (length temp-supports))) (progn (setq temp-supports (vl-remove (nth sel-idx temp-supports) temp-supports)) (update-support-list)) (alert \"삭제할 항목을 선택하세요!\")))")
            (action_tile "btn_clear" "(progn (setq temp-supports '()) (update-support-list))")
            (action_tile "accept" "(progn (setq *tsp-support-list* temp-supports) (done_dialog 1))")
            (action_tile "back" "(done_dialog 2)") 
            (action_tile "cancel" "(done_dialog 0)")
            
            (setq result (start_dialog))
          )
        )
      )
    )


   ;; [4 신호] 공통 도면 작도 처리 (순수 수학 연산, 동적 배열 및 화면 즉시 갱신)
    (if (= result 4)
      (progn
        ;; =====================================================================
        ;; 통합 모드: 도면 즉시 갱신 (다이얼로그에서 변경된 사항을 도면에 먼저 렌더링)
        (princ "\n[시스템] 미리보기 갱신...")
        
        ;; 기존 manual-pts 로드 및 안전 보존 (ESC 복구용 백업)
        (setq orig-manual-pts (if (> (length restore-data) 8) (nth 8 restore-data) '()))
        
        ;; 작도를 위해 화면을 깨끗하게 비우도록 manual-pts를 nil로 만든 preview-data 생성
        (setq real-type (if (wcmatch (nth 2 restore-data) "*Anchor*") "앵커(Earth Anchor)" "버팀보(Strut)"))
        (setq preview-data (list real-type (nth 1 restore-data) (nth 2 restore-data) (nth 3 restore-data) 
                                 (nth 4 restore-data) (nth 5 restore-data) (nth 6 restore-data) (nth 7 restore-data) 
                                 '() ;; 화면을 비우기 위해 빈 리스트 할당
                                 (nth 9 restore-data) (nth 10 restore-data) (nth 11 restore-data)))

        ;; 1. 현재 추가/수정 중인 데이터를 기존 임시 리스트에 병합 (비워진 데이터로)
        (setq preview-supports temp-supports)
        (if (= restore-type "ADD")
          (setq preview-supports (append preview-supports (list preview-data)))
          (progn
            (setq i 0 new-list '())
            (foreach item preview-supports
              (if (= i restore-idx)
                (setq new-list (append new-list (list preview-data)))
                (setq new-list (append new-list (list item)))
              )
              (setq i (1+ i))
            )
            (setq preview-supports new-list)
          )
        )
        
        ;; 2. 현재 편집 중인 세그먼트의 'SUPPORT-LIST'를 최신 미리보기 데이터로 덮어쓰기
        (if (and (boundp '*tsp-current-seg-idx*) *tsp-current-seg-idx*)
          (setq *segment-list* (subst (subst (cons 'SUPPORT-LIST preview-supports) 
                              (assoc 'SUPPORT-LIST (nth *tsp-current-seg-idx* *segment-list*)) 
                              (nth *tsp-current-seg-idx* *segment-list*))
                       (nth *tsp-current-seg-idx* *segment-list*)
                       *segment-list*))
        )
        
        ;; 3. 화면 갱신 수행 
        ;; 하위 함수 직접 호출을 차단하고, 청소 로직이 포함된 tsp-redraw-realtime-plan을 호출하여 보강재 잔류 방지
        (if (boundp 'tsp-redraw-realtime-plan)
          (tsp-redraw-realtime-plan *tsp-boundary-ent* *tsp-boundary-orient*)
          (create-hpile-set-on-boundary *tsp-boundary-ent* *tsp-boundary-orient*)
        )
        ;; =====================================================================

        ;; [C.T.C 간격 동기화] (인덱스 10번으로 수정)
        (setq ctc-input (if (and restore-data (> (length restore-data) 10) (nth 10 restore-data) (/= (nth 10 restore-data) "")) 
                          (atof (nth 10 restore-data)) 
                          5.0))
        (if (<= ctc-input 0.0) (setq ctc-input 5.0))
        (setq ctc-dist (* ctc-input 1000.0))

        ;; 작도 시작 기준(start-mode) 판별 (0:사용자 클릭, 1:세그먼트 중점, 2:간격 중심) - 인덱스 9번으로 수정
        (setq start-mode (if (> (length restore-data) 9) (nth 9 restore-data) "0"))

        (if (and (or (= start-mode "1") (= start-mode "2")) *tsp-current-seg-idx*)
          (progn
            ;; 전역변수에 저장된 현재 세그먼트의 중점 좌표를 WCS로 자동 도출하여 클릭 생략
            (setq p-start-v (cdr (assoc 'V-START (nth *tsp-current-seg-idx* *segment-list*))))
            (setq p-end-v (cdr (assoc 'V-END (nth *tsp-current-seg-idx* *segment-list*))))
            (setq p-start-wcs (trans p-start-v *tsp-boundary-ent* 0))
            (setq p-end-wcs (trans p-end-v *tsp-boundary-ent* 0))
            (setq pt-user (list (/ (+ (car p-start-wcs) (car p-end-wcs)) 2.0)
                                (/ (+ (cadr p-start-wcs) (cadr p-end-wcs)) 2.0)
                                0.0))
            (princ "\n[자동 시작] 선택된 세그먼트의 중점에서 배열 작도를 즉시 시작합니다.")
          )
          (progn
            ;; 옵션이 0(사용자 클릭)이거나 세그먼트 정보를 찾지 못했을 때는 기존처럼 클릭 요청
            (princ "\n[수동 작도] 버팀보(Strut)를 설치할 기준 벽체(경계선) 근처를 1번만 클릭하세요 (취소: ESC/우클릭): ")
            (setq pt-user (vl-catch-all-apply 'getpoint))
          )
        )
        
        (if (vl-catch-all-error-p pt-user)
          (progn
            (princ "\n[취소] ESC 입력 감지. 작도를 취소하고 입력창으로 돌아갑니다.")
            (setq restore-action T)
          )
          (if pt-user
            (progn
              ;; 흙막이 전체 정점 WCS 변환 (PIP 내부 판별용) - 성능을 위해 1회만 계산
              (setq poly-verts (mapcar '(lambda (x / v) 
                                          (setq v (trans (cdr (assoc 'V-START x)) *tsp-boundary-ent* 0))
                                          (list (car v) (cadr v) 0.0)
                                        ) 
                                        *segment-list*))

              ;; 세그먼트 경계 제한을 위한 점-세그먼트 인덱스 판별 함수
              (defun get-seg-idx-for-pt (pt / min-d idx i p1 p2 d)
                (setq min-d 1e99 idx 0 i 0)
                (foreach seg *segment-list*
                  (setq p1 (cdr (assoc 'V-START seg)))
                  (setq p2 (cdr (assoc 'V-END seg)))
                  (setq d (abs (- (+ (distance p1 pt) (distance pt p2)) (distance p1 p2))))
                  (if (< d min-d) (progn (setq min-d d idx i)))
                  (setq i (1+ i))
                )
                idx
              )

              ;;;; ----------------------------------------------------------------------
              ;;;; 내부 함수: draw-dynamic-strut
              ;;;; 기준점(bp)을 받아 벽체를 추적하고, 맞은편 레이저를 쏴서 즉시 작도하는 캡슐화 함수
              ;;;; ----------------------------------------------------------------------
              (defun draw-dynamic-strut (bp / res-ents min-dist seg-idx1 i best-seg1 p1 p2 d p-base-flat tang-ang norm-ang1 norm-ang2 p-ray1 p-ray2 pts sp1 sp2 sp1-flat sp2-flat int-pt1 int-pt2 valid-pts int-pt mid-pt p-opp seg-idx2 norm-ang offset1 offset2 pt1 pt2)
                (setq res-ents nil)
                
                ;; 현재 점(bp)이 속한 선분 파악
                (setq min-dist 1e99 seg-idx1 0 i 0 best-seg1 nil)
                (foreach seg *segment-list*
                  (setq p1 (cdr (assoc 'V-START seg)))
                  (setq p2 (cdr (assoc 'V-END seg)))
                  (setq d (abs (- (+ (distance p1 bp) (distance bp p2)) (distance p1 p2))))
                  (if (< d min-dist)
                    (progn (setq min-dist d seg-idx1 i best-seg1 seg))
                  )
                  (setq i (1+ i))
                )
                
                ;; 양방향 수직 레이저 발사
                (setq p-base-flat (list (car bp) (cadr bp) 0.0))
                (setq p1 (trans (cdr (assoc 'V-START best-seg1)) *tsp-boundary-ent* 0))
                (setq p2 (trans (cdr (assoc 'V-END best-seg1)) *tsp-boundary-ent* 0))
                (setq p1 (list (car p1) (cadr p1) 0.0))
                (setq p2 (list (car p2) (cadr p2) 0.0))
                
                (setq tang-ang (angle p1 p2))
                (setq norm-ang1 (+ tang-ang (/ pi 2.0)))
                (setq norm-ang2 (- tang-ang (/ pi 2.0)))
                
                (setq p-ray1 (polar p-base-flat norm-ang1 1e6))
                (setq p-ray2 (polar p-base-flat norm-ang2 1e6))
                
                (setq pts '() i 0)
                (foreach seg *segment-list*
                  (setq sp1 (trans (cdr (assoc 'V-START seg)) *tsp-boundary-ent* 0))
                  (setq sp2 (trans (cdr (assoc 'V-END seg)) *tsp-boundary-ent* 0))
                  (setq sp1-flat (list (car sp1) (cadr sp1) 0.0))
                  (setq sp2-flat (list (car sp2) (cadr sp2) 0.0))
                  
                  (setq int-pt1 (inters p-base-flat p-ray1 sp1-flat sp2-flat T))
                  (setq int-pt2 (inters p-base-flat p-ray2 sp1-flat sp2-flat T))
                  
                  (if (and int-pt1 (> (distance p-base-flat int-pt1) 10.0))
                    (setq pts (append pts (list (list int-pt1 i norm-ang1))))
                  )
                  (if (and int-pt2 (> (distance p-base-flat int-pt2) 10.0))
                    (setq pts (append pts (list (list int-pt2 i norm-ang2))))
                  )
                  (setq i (1+ i))
                )
                
                ;; 교차점 내부 검증 (PIP) 및 맞은편 벽체 도출
                (setq valid-pts '())
                (foreach pt-data pts
                  (setq int-pt (car pt-data))
                  (setq mid-pt (list (/ (+ (car p-base-flat) (car int-pt)) 2.0) (/ (+ (cadr p-base-flat) (cadr int-pt)) 2.0) 0.0))
                  (if (tsp-is-point-inside mid-pt poly-verts)
                    (setq valid-pts (append valid-pts (list pt-data)))
                  )
                )
                
                (if valid-pts
                  (progn
                    (setq valid-pts (vl-sort valid-pts '(lambda (a b) (< (distance p-base-flat (car a)) (distance p-base-flat (car b))))))
                    (setq p-opp (car (car valid-pts)))
                    (setq seg-idx2 (cadr (car valid-pts)))
                    (setq norm-ang (caddr (car valid-pts)))
                    
                    (setq offset1 (tsp-get-wale-offset (nth seg-idx1 *segment-list*)))
                    (setq offset2 (tsp-get-wale-offset (nth seg-idx2 *segment-list*)))
                    
                    (if (> (distance bp p-opp) (+ offset1 offset2))
                      (progn
                        (setq pt1 (polar bp norm-ang offset1))
                        (setq pt2 (polar p-opp (+ norm-ang pi) offset2))
                        
                        (if (wcmatch (nth 2 restore-data) "H형강")
                          (progn
                            ;; XDATA 및 옵션 전달을 위한 데이터 파싱
                            (setq sec-str (nth 6 restore-data))
                            (setq res-count (nth 4 restore-data))
                            (setq is-double (if (>= res-count 2) T nil))
                            (setq s-brace-opt (if (> (length restore-data) 11) (nth 11 restore-data) nil))
                            (setq target-seg-id (cdr (assoc 'ID (nth seg-idx1 *segment-list*))))
                            
                            ;; 배열 시 개별 보강재 작도 차단 (연속 보강재 일괄 작도를 위해)
                            (setq array-brace-opt s-brace-opt)
                            (if array-brace-opt (setq array-brace-opt (cons "0" (cdr array-brace-opt))))
                            
                            ;; --- 50m 자중 좌굴 한계 검사 및 취소(Cancel) 팝업 ---
                            (setq actual-strut-len (distance pt1 pt2))
                            (setq proceed-draw T)
                            (if (> actual-strut-len 50000.0)
                              (progn
                                (setq wsh (vlax-create-object "WScript.Shell"))
                                ;; 팝업 코드 33 = 1(확인/취소 버튼) + 32(물음표 아이콘)
                                (setq msg-res (vlax-invoke-method wsh 'Popup (strcat "경고: 버팀보 산정 길이(" (rtos (/ actual-strut-len 1000.0) 2 1) "m)가 자중 좌굴 한계(50m)를 초과합니다.\n\n안전성에 유의하여 작도를 계속 진행하시겠습니까?") 0 "TSP - 자중 좌굴 한계 초과" 33))
                                (vlax-release-object wsh)
                                (if (= msg-res 2) (setq proceed-draw nil)) ; 2는 사용자가 '취소'를 선택했음을 의미
                              )
                            )
                            
                            (if proceed-draw
                              (progn
                                ;; 확장된 매개변수를 적용하여 작도 함수 호출
                                (setq drawn-ents (tsp-draw-manual-strut pt1 pt2 sec-str (nth 7 restore-data) is-double array-brace-opt target-seg-id))
                                
                                ;; 작도된 객체 리스트와 시작점(pt1) 반환 및 보강재를 위한 실시간 제원 갱신
                                (if drawn-ents 
                                  (progn 
                                    (setq res-ents (list drawn-ents pt1))
                                    ;; 방금 작도한 버팀보의 각도와 길이를 갱신하여, 후속 보강재 작도 시 과거 데이터가 쓰이는 것을 차단
                                    (setq strut-ang (angle pt1 pt2))
                                    (setq strut-len (distance pt1 pt2))
                                  )
                                )
                              )
                              (princ (strcat "\n[작도 취소] 버팀보(길이: " (rtos (/ actual-strut-len 1000.0) 2 1) "m) 배치가 사용자에 의해 취소되었습니다."))
                            )
                          )
                          (princ "\n[알림] 강관 버팀보는 평면 작도가 지원되지 않습니다.")
                        )
                      )
                      (princ "\n[오류] 띠장 두께 합산값이 양쪽 벽체 간격보다 커서 설치 불가합니다.")
                    )
                  )
                  (princ "\n[경고] 반대편 벽체를 찾을 수 없는 구간입니다.")
                )
                res-ents ;; (작도된_객체_리스트 진짜_pt1) 형태로 반환
              )
              ;;;; ----------------------------------------------------------------------

              ;; 1. 기준점 보정 및 작도 시작 기준(Start Mode) 적용
              (setq p-base-click (vlax-curve-getClosestPointTo *tsp-boundary-ent* pt-user))
              (setq target-seg-idx (get-seg-idx-for-pt p-base-click)) ;; 첫 클릭 위치의 종속 세그먼트 인덱스 기록
              
              (setq start-mode (if (> (length restore-data) 9) (nth 9 restore-data) "0"))
              
              (if (or (= start-mode "1") (= start-mode "2"))
                (progn
                  ;; 모서리 시작/끝점을 통해 세그먼트 중점(Midpoint) 도출
                  (setq p-start-v   (cdr (assoc 'V-START (nth target-seg-idx *segment-list*))))
                  (setq p-end-v     (cdr (assoc 'V-END   (nth target-seg-idx *segment-list*))))
                  (setq p-start-wcs (trans p-start-v *tsp-boundary-ent* 0))
                  (setq p-end-wcs   (trans p-end-v   *tsp-boundary-ent* 0))
                  (setq mid-pt (list (/ (+ (car p-start-wcs) (car p-end-wcs)) 2.0)
                   (/ (+ (cadr p-start-wcs) (cadr p-end-wcs)) 2.0) 0.0))
                  (setq p-base (vlax-curve-getClosestPointTo *tsp-boundary-ent* mid-pt))
                )
                (setq p-base p-base-click)
              )
              
              ;; 기존 임시 객체 초기화 (중첩 방지)
              (foreach e manual-drawn-ents (if (entget e) (vl-catch-all-apply 'entdel (list e))))
              (setq manual-drawn-ents '())
              
              (setq is-curve-closed (vlax-curve-isClosed *tsp-boundary-ent*))
              (setq max-dist-curve (vlax-curve-getDistAtParam *tsp-boundary-ent* (vlax-curve-getEndParam *tsp-boundary-ent*)))
              (setq cur-dist (vlax-curve-getDistAtPoint *tsp-boundary-ent* p-base))
              
              ;; 2. 화면 좌/우 방향 동기화 
              (setq param-base (vlax-curve-getParamAtPoint *tsp-boundary-ent* p-base))
              (setq deriv (vlax-curve-getFirstDeriv *tsp-boundary-ent* param-base))
              (setq screen-ang (angle '(0 0 0) deriv))
              
              (setq dir-sign 1)
              (cond
                ((< (cos screen-ang) -1e-4) (setq dir-sign -1))
                ((and (< (abs (cos screen-ang)) 1e-4) (< (sin screen-ang) -1e-4)) (setq dir-sign -1))
              )

              ;; 모드별 초기 버팀보 작도 분기 및 초기 점(init-pts) 수집
              (setq init-ents '())
              (setq init-pts '())
              (if (= start-mode "2") ; 간격 중심 시작 (중앙 비우고 양쪽 배치)
                (progn
                  (setq dist-L (- cur-dist (* dir-sign (/ ctc-dist 2.0))))
                  (setq dist-R (+ cur-dist (* dir-sign (/ ctc-dist 2.0))))
                  
                  (if (< dist-L 0.0) (setq dist-L (if is-curve-closed (+ max-dist-curve dist-L) nil)))
                  (if (and dist-L (> dist-L max-dist-curve)) (setq dist-L (if is-curve-closed (- dist-L max-dist-curve) nil)))
                  
                  (if (> dist-R max-dist-curve) (setq dist-R (if is-curve-closed (- dist-R max-dist-curve) nil)))
                  (if (and dist-R (< dist-R 0.0)) (setq dist-R (if is-curve-closed (+ max-dist-curve dist-R) nil)))
                  
                  (setq ents-L '() ents-R '())
                  (if dist-L 
                    (progn
                      (setq p-L (vlax-curve-getPointAtDist *tsp-boundary-ent* dist-L))
                      (if (= (get-seg-idx-for-pt p-L) target-seg-idx) 
                        (progn
                          (setq res-L (draw-dynamic-strut p-L))
                          (if res-L (progn (setq ents-L (car res-L)) (setq init-pts (append init-pts (list (cadr res-L))))))
                        )
                      )
                    )
                  )
                  (if dist-R 
                    (progn
                      (setq p-R (vlax-curve-getPointAtDist *tsp-boundary-ent* dist-R))
                      (if (= (get-seg-idx-for-pt p-R) target-seg-idx) 
                        (progn
                          (setq res-R (draw-dynamic-strut p-R))
                          (if res-R (progn (setq ents-R (car res-R)) (setq init-pts (append init-pts (list (cadr res-R))))))
                        )
                      )
                    )
                  )
                  (setq init-ents (append ents-L ents-R))
                  (setq dist-A dist-L dist-D dist-R)
                )
                (progn ; 0: 클릭 위치, 1: 세그먼트 중점
                  (setq res-base (draw-dynamic-strut p-base))
                  (if res-base (progn (setq init-ents (car res-base)) (setq init-pts (list (cadr res-base)))))
                  (setq dist-A cur-dist dist-D cur-dist)
                )
              )
              
              (if init-ents
                (progn
                  (setq manual-drawn-ents (append manual-drawn-ents init-ents))
                  (command "_.REGEN")
                  (princ "\n[성공] 기준 위치 설정 및 초기 작도 완료.")
                  
                  (setq strut-history '())
                  (setq temp-brace-ents '())
                  
                  ;; 상위 제원 상태 박제
                  (setq main-sec-str (nth 6 restore-data))
                  (setq main-is-double (if (>= (nth 4 restore-data) 2) T nil))
                  (setq main-s-brace-opt (if (> (length restore-data) 11) (nth 11 restore-data) nil))
                  
                  (setq loop-grread T)
                  (setq return-to-dialog nil)
                  (setq commit-drawing nil)
                  
                  ;; 순수 좌표 집계 방식의 실시간 연속 보강재 오버레이 함수
                  (defun update-dynamic-braces ( / all-pts hist active-seg-id )
                    (foreach e temp-brace-ents (if (entget e) (vl-catch-all-apply 'entdel (list e))))
                    (setq temp-brace-ents '())
                    (if (and main-s-brace-opt (= (nth 0 main-s-brace-opt) "1"))
                      (progn
                        ;; XDATA에 의존하지 않고 grread 입력 배열 점들을 직접 리스트로 실시간 결합
                        (setq all-pts init-pts)
                        (foreach hist strut-history
                          (setq all-pts (append all-pts (caddr hist)))
                        )
                        ;; 현재 작업 중인 세그먼트 ID 추출 방어 로직 적용
      (setq active-seg-id (if (and target-seg-idx (nth target-seg-idx *segment-list*)) (cdr (assoc 'ID (nth target-seg-idx *segment-list*))) 0))
      
      ;; [안전 바인딩(Fallback) 보강] 실제 작도된 버팀보의 양끝단 좌표를 추적하여 실시간 길이를 mm단위로 도출
      (setq cur-strut-len strut-len)
      (if (and all-pts (> (length all-pts) 0) (listp (car all-pts)) (= (length (car all-pts)) 2))
        (setq cur-strut-len (distance (caar all-pts) (cadar all-pts)))
      )
      
      ;; 혹시라도 실시간 좌표 추출에 실패했을 경우를 대비한 최후의 방어막
      (if (or (null cur-strut-len) (= cur-strut-len 0.0))
        (setq cur-strut-len (if (and target-seg-idx (nth target-seg-idx *segment-list*))
                          (cdr (assoc 'LENGTH (nth target-seg-idx *segment-list*)))
                          0.0))
      )

      (if (null strut-ang)
        (setq strut-ang (if (and target-seg-idx (nth target-seg-idx *segment-list*))
                          (cdr (assoc 'ANGLE (nth target-seg-idx *segment-list*)))
                          0.0))
      )

      ;; 정밀 추적용 인자 리스트 구조 확장 호출 (실시간 갱신된 실제 길이 cur-strut-len 적용)
      (setq temp-brace-ents (tsp-draw-realtime-continuous-braces all-pts main-s-brace-opt main-sec-str main-is-double strut-ang cur-strut-len active-seg-id))
                      )
                    )
                  )
                  (update-dynamic-braces) ;; 최초 작도 시 배치 적용
                  
                  (princ "\n[배열 모드] A: 왼쪽 | D: 오른쪽 | W: 양측 동시 | S: 취소(Undo) | B: 입력창 복귀 | Enter/Space/우클릭: 완료")
                  
                  ;; 3. 동적 배열(grread) 루프 시작 (ESC 안전 방어 적용)
                  (while loop-grread
                    (setq gr (vl-catch-all-apply 'grread (list T 12 0)))
                    (if (vl-catch-all-error-p gr)
                      (progn
                        ;; ESC Pressed during grread
                        (foreach e manual-drawn-ents (if (entget e) (vl-catch-all-apply 'entdel (list e))))
                        (foreach e temp-brace-ents (if (entget e) (vl-catch-all-apply 'entdel (list e))))
                        (setq manual-drawn-ents '() temp-brace-ents '())
                        (setq loop-grread nil return-to-dialog T)
                        (princ "\n[취소] ESC 입력 감지. 작도를 취소하고 입력창으로 돌아갑니다.")
                      )
                      (progn
                        (setq code (car gr) val (cadr gr))
                        (cond
                          ((= code 2) ;; 키보드 입력
                           (cond
                             ;; [B 키] 입력창으로 돌아가기 (안전장치)
                             ((or (= val 66) (= val 98))
                              (foreach e manual-drawn-ents (if (entget e) (vl-catch-all-apply 'entdel (list e))))
                              (foreach e temp-brace-ents (if (entget e) (vl-catch-all-apply 'entdel (list e))))
                              (setq manual-drawn-ents '() temp-brace-ents '())
                              (setq loop-grread nil return-to-dialog T)
                              (princ "\n[취소] B키 입력 감지. 작도를 취소하고 입력창으로 돌아갑니다.")
                             )
                             ;; [A 키] 화면 왼쪽 복사
                             ((or (= val 65) (= val 97))
                              (setq next-dist (- dist-A (* dir-sign ctc-dist)))
                              (if (< next-dist 0.0) (setq next-dist (if is-curve-closed (+ max-dist-curve next-dist) nil)))
                              (if (and next-dist (> next-dist max-dist-curve)) (setq next-dist (if is-curve-closed (- next-dist max-dist-curve) nil)))
                              (if next-dist
                                (progn
                                  (setq new-p-base (vlax-curve-getPointAtDist *tsp-boundary-ent* next-dist))
                                  (if (/= (get-seg-idx-for-pt new-p-base) target-seg-idx)
                                    (princ "\n[알림] 현재 세그먼트 경계를 벗어나 작도를 중단합니다.")
                                    (progn
                                      (setq res-A (draw-dynamic-strut new-p-base))
                                      (if res-A
                                        (progn
                                          (setq new-ents (car res-A) real-pt1 (cadr res-A))
                                          (setq strut-history (cons (list 'A new-ents (list real-pt1) dist-A) strut-history))
                                          (setq dist-A next-dist manual-drawn-ents (append manual-drawn-ents new-ents))
                                          (update-dynamic-braces) ;; 실시간 보강재 갱신
                                          (princ (strcat "\n[추가] 좌측 C.T.C " (rtos ctc-input 2 2) "m 배열 완료."))
                                        )
                                      )
                                    )
                                  )
                                )
                                (princ "\n[알림] 경계선의 끝에 도달하여 더 이상 왼쪽으로 배열할 수 없습니다.")
                              )
                             )
                             ;; [D 키] 화면 오른쪽 복사
                             ((or (= val 68) (= val 100))
                              (setq next-dist (+ dist-D (* dir-sign ctc-dist)))
                              (if (> next-dist max-dist-curve) (setq next-dist (if is-curve-closed (- next-dist max-dist-curve) nil)))
                              (if (and next-dist (< next-dist 0.0)) (setq next-dist (if is-curve-closed (+ max-dist-curve next-dist) nil)))
                               (if next-dist
                                (progn
                                  (setq new-p-base (vlax-curve-getPointAtDist *tsp-boundary-ent* next-dist))
                                  (if (/= (get-seg-idx-for-pt new-p-base) target-seg-idx)
                                    (princ "\n[알림] 현재 세그먼트 경계를 벗어나 작도를 중단합니다.")
                                    (progn
                                      (setq res-D (draw-dynamic-strut new-p-base))
                                      (if res-D
                                        (progn
                                          (setq new-ents (car res-D) real-pt1 (cadr res-D))
                                          (setq strut-history (cons (list 'D new-ents (list real-pt1) dist-D) strut-history))
                                          (setq dist-D next-dist manual-drawn-ents (append manual-drawn-ents new-ents))
                                          (update-dynamic-braces) ;; 실시간 보강재 갱신
                                          (princ (strcat "\n[추가] 우측 C.T.C " (rtos ctc-input 2 2) "m 배열 완료."))
                                        )
                                      )
                                    )
                                  )
                                )
                                (princ "\n[알림] 경계선의 끝에 도달하여 더 이상 오른쪽으로 배열할 수 없습니다.")
                              )
                             )
                             ;; [W 키] 양쪽 동시 복사
                              ((or (= val 87) (= val 119))
                               (setq combined-ents '() cur-w-pts '() orig-dist-A dist-A orig-dist-D dist-D)
                               ;; 좌측 계산
                               (setq next-dist-L (- dist-A (* dir-sign ctc-dist)))
                               (if (< next-dist-L 0.0) (if is-curve-closed (setq next-dist-L (+ max-dist-curve next-dist-L)) (setq next-dist-L nil)))
                               (if (and next-dist-L (> next-dist-L max-dist-curve)) (setq next-dist-L (if is-curve-closed (- next-dist-L max-dist-curve) nil)))
                               (if next-dist-L
                                 (progn
                                   (setq new-p-base-L (vlax-curve-getPointAtDist *tsp-boundary-ent* next-dist-L))
                                   (if (/= (get-seg-idx-for-pt new-p-base-L) target-seg-idx)
                                     (princ "\n[알림] 좌측은 현재 세그먼트 경계를 벗어났습니다.")
                                     (progn
                                       (setq res-L (draw-dynamic-strut new-p-base-L))
                                       (if res-L (progn (setq ents-L (car res-L) real-pt1-L (cadr res-L)) (setq combined-ents (append combined-ents ents-L) dist-A next-dist-L cur-w-pts (append cur-w-pts (list real-pt1-L)))))
                                     )
                                   )
                                 )
                               )
                               ;; 우측 계산
                               (setq next-dist-R (+ dist-D (* dir-sign ctc-dist)))
                               (if (> next-dist-R max-dist-curve) (if is-curve-closed (setq next-dist-R (- next-dist-R max-dist-curve)) (setq next-dist-R nil)))
                               (if (and next-dist-R (< next-dist-R 0.0)) (setq next-dist-R (if is-curve-closed (+ max-dist-curve next-dist-R) nil)))
                               (if next-dist-R
                                 (progn
                                   (setq new-p-base-R (vlax-curve-getPointAtDist *tsp-boundary-ent* next-dist-R))
                                   (if (/= (get-seg-idx-for-pt new-p-base-R) target-seg-idx)
                                     (princ "\n[알림] 우측은 현재 세그먼트 경계를 벗어났습니다.")
                                     (progn
                                       (setq res-R (draw-dynamic-strut new-p-base-R))
                                       (if res-R (progn (setq ents-R (car res-R) real-pt1-R (cadr res-R)) (setq combined-ents (append combined-ents ents-R) dist-D next-dist-R cur-w-pts (append cur-w-pts (list real-pt1-R)))))
                                     )
                                   )
                                 )
                               )
                               (if combined-ents
                                 (progn
                                   (setq strut-history (cons (list 'W combined-ents cur-w-pts orig-dist-A orig-dist-D) strut-history))
                                   (setq manual-drawn-ents (append manual-drawn-ents combined-ents))
                                   (update-dynamic-braces) ;; 실시간 보강재 갱신
                                   (princ "\n[추가] 양측 동시 배열 작도 완료.")
                                 )
                                 (princ "\n[알림] 양쪽 모두 경계선 끝에 도달했습니다.")
                               )
                              )
                             ;; [M 키] 도면 거리 측정 (Measure)
                              ((or (= val 77) (= val 109))
                               (princ "\n[측정] 시작점을 클릭하세요 (객체 스냅 사용 가능): ")
                               (setq m-pt1 (getpoint))
                               (if m-pt1
                                 (progn
                                   (princ "\n[측정] 끝점을 클릭하세요: ")
                                   (setq m-pt2 (getpoint m-pt1))
                                   (if m-pt2
                                     (progn
                                       (setq m-dist (distance m-pt1 m-pt2))
                                       (alert (strcat "측정 거리: " (rtos m-dist 2 1) " mm (" (rtos (/ m-dist 1000.0) 2 3) " m)"))
                                       (princ (strcat "\n>> 측정 완료: " (rtos m-dist 2 1) " mm"))
                                     )
                                   )
                                 )
                                )
                               (princ "\n[배열 모드] A: 왼쪽 | D: 오른쪽 | W: 양측 동시 | S: 취소 | M: 거리 측정 | B: 복귀 | Enter/Space/우클릭: 완료")
                              )
                             ;; [S 키] 실행 취소 (Undo)
                             ((or (= val 83) (= val 115))
                              (if (> (length strut-history) 0)
                                (progn
                                  (setq last-action (car strut-history) act-type (car last-action) act-ents (cadr last-action))
                                  (foreach e act-ents (if (entget e) (vl-catch-all-apply 'entdel (list e))))
                                  ;; 취소된 객체를 리스트에서 제외하여 실시간 보강재 연산에서 제외시킴
                                  (foreach e act-ents (setq manual-drawn-ents (vl-remove e manual-drawn-ents)))
                                  (cond
                                    ((= act-type 'A) (setq dist-A (nth 3 last-action)))
                                    ((= act-type 'D) (setq dist-D (nth 3 last-action)))
                                    ((= act-type 'W) (setq dist-A (nth 3 last-action) dist-D (nth 4 last-action)))
                                  )
                                  (setq strut-history (cdr strut-history))
                                  (update-dynamic-braces) ;; 실시간 보강재 갱신 (줄어든 상태 반영)
                                  (princ "\n[취소] 가장 최근에 추가된 버팀보 배열을 취소(Undo)했습니다.")
                                )
                                (princ "\n[알림] 더 이상 취소할 배열 내역이 없습니다.")
                               )
                             )
                             ;; [Enter 또는 Space] 완료
                             ((or (= val 13) (= val 32))
                              (setq loop-grread nil commit-drawing T)
                              (setq manual-drawn-ents (append manual-drawn-ents temp-brace-ents)) ;; 확정 시 임시 보강재를 영구 리스트에 합병
                              (princ "\n[완료] 동적 배열 작업을 종료하고 다이얼로그로 복귀합니다.")
                             )
                           )
                          )
                          ;; [마우스 우클릭] 완료 처리 (grread 11, 25 코드 대응)
                          ((or (= code 11) (= code 25))
                           (setq loop-grread nil commit-drawing T)
                           (setq manual-drawn-ents (append manual-drawn-ents temp-brace-ents)) ;; 확정 시 임시 보강재를 영구 리스트에 합병
                           (princ "\n[완료] 동적 배열 작업을 종료하고 다이얼로그로 복귀합니다.")
                          )
                        )
                      )
                    )
                  ) ;; end while loop-grread
                  
                  ;; 루프 종료 후 데이터 처리 (완료 vs 취소)
                  (if commit-drawing
                    (progn
                      ;; 정상 완료: 점 데이터 취합 (순서대로 정렬)
                      (setq final-pts init-pts)
                      (foreach hist (reverse strut-history)
                        (setq final-pts (append final-pts (caddr hist)))
                      )
                      ;; 누적(append)하지 않고, 새로 작도한 점으로 완벽히 교체(Replace)
                      (setq manual-pts final-pts)
                      
                      ;; 교체된 점 데이터를 restore-data에 업데이트하여 다이얼로그로 복귀
                      (setq restore-data (list (nth 0 restore-data) (nth 1 restore-data) (nth 2 restore-data) (nth 3 restore-data) 
                                               (nth 4 restore-data) (nth 5 restore-data) (nth 6 restore-data) (nth 7 restore-data) 
                                               manual-pts ;; 새로운 점으로 덮어쓰기
                                               (nth 9 restore-data) (nth 10 restore-data) (nth 11 restore-data)))
                      (setq restore-action T)
                    )
                    (if return-to-dialog
                      (progn
                        ;; 취소(ESC) 시 날아갔던 데이터를 원래 상태로 롤백(Rollback)
                        (setq manual-pts orig-manual-pts)
                        (setq restore-data (list (nth 0 restore-data) (nth 1 restore-data) (nth 2 restore-data) (nth 3 restore-data) 
                                                 (nth 4 restore-data) (nth 5 restore-data) (nth 6 restore-data) (nth 7 restore-data) 
                                                 orig-manual-pts ;; 백업해둔 원래 점으로 복구
                                                 (nth 9 restore-data) (nth 10 restore-data) (nth 11 restore-data)))
                        (setq restore-action T)
                      )
                    )
                  )
                )
                (progn
                  (princ "\n[오류] 기준 위치에 버팀보를 작도할 수 없는 구역입니다.")
                  (setq restore-action T)
                )
              )
            )
            (progn 
              (princ "\n[알림] 기준점 입력이 취소되었습니다. 창으로 돌아갑니다.") 
              (setq manual-pts nil)
              (setq restore-action T)
            )
          )
        )
       )
      )
    
    (if (or (= result 1) (= result 2) (= result 0))
      (setq loop-support nil)
    )
  )
  
  (unload_dialog dcl-id)
  result
)


;;;;==========================================================================
;;;; defun tsp-is-point-inside : 점이 다각형(폴리라인) 내부에 있는지 판별 (Ray-casting 알고리즘)
;;;;==========================================================================
(defun tsp-is-point-inside (pt verts / c i j p1 p2 pt-x pt-y)
  (setq c nil)
  (setq pt-x (car pt) pt-y (cadr pt))
  (setq i 0 j (1- (length verts)))
  (while (< i (length verts))
    (setq p1 (nth i verts) p2 (nth j verts))
    (if (and (not (equal (cadr p1) (cadr p2) 1e-6))
             (or (and (<= (cadr p1) pt-y) (> (cadr p2) pt-y))
                 (and (<= (cadr p2) pt-y) (> (cadr p1) pt-y))))
      (if (< pt-x (+ (car p1) (* (/ (- (car p2) (car p1)) (- (cadr p2) (cadr p1))) (- pt-y (cadr p1)))))
        (setq c (not c))
      )
    )
    (setq j i i (1+ i))
  )
  c
)


;;;;==========================================================================
;;;; defun tsp-draw-manual-strut : 수동 버팀보 평면 객체 작도 (N등분/2H/말뚝 통합)
;;;;==========================================================================
(defun tsp-draw-manual-strut
  (pt1 pt2 sec-str jack-type is-double s-brace-opt seg-id
   / boundary-handle start-ent clean-sec-str strut-vals
     b tw h tf half-b half-tw strut-ang pt-dir jack-len plate-thick
     strut-offsets s-off sub-idx pt-jack-end pt-beam-start pt-beam-end
     pl1-p1 pl1-p2 pl1-p3 pl1-p4 pl2-p1 pl2-p2 pl2-p3 pl2-p4
     p1-out p2-out p3-out p4-out p1-in p2-in p3-in p4-in
     pt-jack-ins jack-block-name jack-rot strut-xdata strut-len
     total-L L-max num-div interval offsets spatial-idx is-valid-post
     invert-val p-center post-rot y_scale p-ins post-block new-ents nxt
     cur-pt1 cur-pt2 b-width stiff-enable slender-limit is-manual
     manual-interval post-enable post-layout post-invert post-side
     i strut-sys-half-width margin brace-len p-brace-1 p-brace-2
     post-half-h lateral-dist mid-gap-xdata)

  ;; 작도 시작 전 마지막 객체를 기억
  (setq start-ent (entlast))
  (setq boundary-handle (tsp-get-entity-handle *tsp-boundary-ent*))

  ;; 1. 제원 파싱 및 레이어 생성 (2H 텍스트 제거 후 순수 규격 파싱)
  (setq clean-sec-str sec-str)
  (if (wcmatch clean-sec-str "2H *")
    (setq clean-sec-str (vl-string-subst "" "2H " clean-sec-str))
  )

  (setq strut-vals (parse-h-spec clean-sec-str))
  (if (null strut-vals)
    (setq strut-vals '(300 300 10 15))
  )

  (setq h (nth 0 strut-vals)
        b (nth 1 strut-vals)
        tw (nth 2 strut-vals)
        tf (nth 3 strut-vals))

  (setq half-b (/ b 2.0)
        half-tw (/ tw 2.0))

  (create-layer-if-not-exists "_버팀보(Strut)" "3")
  (create-layer-if-not-exists "_중간말뚝(Post pile)" "3")
  (create-layer-if-not-exists "_보강재(Brace)" "7")

  (if (not (tblsearch "LTYPE" "DASHED"))
    (vl-catch-all-apply
      'vla-load
      (list
        (vla-get-linetypes (vla-get-activedocument (vlax-get-acad-object)))
        "DASHED"
        (if (= (getvar "MEASUREMENT") 1) "acadiso.lin" "acad.lin")
      )
    )
  )

  (create-strut-jack-block)
  (create-strut-screw-jack-block)

  ;; 2. 각도, 방향 및 오프셋(2H) 설정
  (setq strut-ang (angle pt1 pt2))
  (setq pt-dir (+ strut-ang (/ pi 2.0)))
  (setq strut-len (distance pt1 pt2))

  ;; 2H 맞버팀대 여부에 따른 작도 오프셋 (기본 0.0, 2H는 폭(b)만큼 이격)
  (setq b-width b)
  (setq strut-offsets (if is-double (list b-width (- b-width)) (list 0.0)))

  ;; 전체 버팀보 시스템의 중심 기준 절반 폭
  ;; 1H는 b/2, 2H는 b이격 + b/2 = 1.5b
  (setq strut-sys-half-width (if is-double (* b 1.5) (/ b 2.0)))

  ;; XDATA 공통 생성 (세그먼트 식별 및 수동 제어용 정보 박제)
  (if (not (tblsearch "APPID" "TSP_STRUT_SPEC"))
    (regapp "TSP_STRUT_SPEC")
  )

  (setq strut-xdata
    (list
      -3
      (list
        "TSP_STRUT_SPEC"
        (cons 1070 seg-id)
        (cons 1040 (float (* strut-sys-half-width 2.0))) ;; XDATA 식별용 가상 폭(RECT 검증용)
        (cons 1010 pt1)
        (cons 1010 pt2)
        (cons 1040 (float h))
        (cons 1040 (float tw))
        (cons 1040 (float tf))
        (cons 1000 "MANUAL_STRUT")
        (cons 1000 boundary-handle)
        (cons 1040 (float b))
      )
    )
  )

  ;; 3. 메인 부재(Flange, Web) 및 잭(Jack) 반복 작도 (1H or 2H)
  (setq sub-idx 0)

  (foreach s-off strut-offsets
    (setq cur-pt1 (polar pt1 pt-dir s-off))
    (setq cur-pt2 (polar pt2 pt-dir s-off))

    (setq jack-len 583.0
          plate-thick 14.0)

    ;; 함수: tsp-draw-manual-strut 내부 마감판 좌표 산출 및 교체 영역
    ;; 맞버팀대의 경우 잭 위치를 지그재그로 교차 배치
    (if (and is-double (= sub-idx 1))
      (progn
        (setq pt-jack-end (polar cur-pt2 (+ strut-ang pi) jack-len))
        (setq pt-beam-start (polar cur-pt1 strut-ang plate-thick))
        (setq pt-beam-end (polar pt-jack-end (+ strut-ang pi) plate-thick))
        (setq pt-jack-ins cur-pt2)
        (setq jack-rot (+ strut-ang pi))

        ;; 마감판 1 좌표 산출 (cur-pt1 ~ pt-beam-start 구간)
        (setq pl1-p1 (polar cur-pt1 pt-dir half-b)
              pl1-p2 (polar pt-beam-start pt-dir half-b))
        (setq pl1-p3 (polar pt-beam-start (- pt-dir pi) half-b)
              pl1-p4 (polar cur-pt1 (- pt-dir pi) half-b))

        ;; 마감판 2 좌표 산출 (pt-beam-end ~ pt-jack-end 구간)
        (setq pl2-p1 (polar pt-beam-end pt-dir half-b)
              pl2-p2 (polar pt-jack-end pt-dir half-b))
        (setq pl2-p3 (polar pt-jack-end (- pt-dir pi) half-b)
              pl2-p4 (polar pt-beam-end (- pt-dir pi) half-b))
      )
      (progn
        (setq pt-jack-end (polar cur-pt1 strut-ang jack-len))
        (setq pt-beam-start (polar pt-jack-end strut-ang plate-thick))
        (setq pt-beam-end (polar cur-pt2 (+ strut-ang pi) plate-thick))
        (setq pt-jack-ins cur-pt1)
        (setq jack-rot strut-ang)

        ;; 마감판 1 좌표 산출 (pt-jack-end ~ pt-beam-start 구간)
        (setq pl1-p1 (polar pt-jack-end pt-dir half-b)
              pl1-p2 (polar pt-beam-start pt-dir half-b))
        (setq pl1-p3 (polar pt-beam-start (- pt-dir pi) half-b)
              pl1-p4 (polar pt-jack-end (- pt-dir pi) half-b))

        ;; 마감판 2 좌표 산출 (pt-beam-end ~ cur-pt2 구간)
        (setq pl2-p1 (polar pt-beam-end pt-dir half-b)
              pl2-p2 (polar cur-pt2 pt-dir half-b))
        (setq pl2-p3 (polar cur-pt2 (- pt-dir pi) half-b)
              pl2-p4 (polar pt-beam-end (- pt-dir pi) half-b))
      )
    )

    ;; 외곽선(Flange) 작도
    (setq p1-out (polar pt-beam-start pt-dir half-b)
          p2-out (polar pt-beam-end pt-dir half-b))
    (setq p3-out (polar pt-beam-start (- pt-dir pi) half-b)
          p4-out (polar pt-beam-end (- pt-dir pi) half-b))

    (entmake
      (append
        (list
          '(0 . "LWPOLYLINE")
          '(100 . "AcDbEntity")
          '(100 . "AcDbPolyline")
          '(8 . "_버팀보(Strut)")
          '(62 . 3)
          '(90 . 4)
          '(70 . 1)
          (list 10 (car p1-out) (cadr p1-out))
          (list 10 (car p2-out) (cadr p2-out))
          (list 10 (car p4-out) (cadr p4-out))
          (list 10 (car p3-out) (cadr p3-out)))
        (list strut-xdata)
      )
    )

    ;; 양 끝단 마감판(End Plate) 1 및 2 생성
    (entmake
      (append
        (list
          '(0 . "LWPOLYLINE")
          '(100 . "AcDbEntity")
          '(100 . "AcDbPolyline")
          '(8 . "_버팀보(Strut)")
          '(62 . 3)
          '(90 . 4)
          '(70 . 1)
          (list 10 (car pl1-p1) (cadr pl1-p1))
          (list 10 (car pl1-p2) (cadr pl1-p2))
          (list 10 (car pl1-p3) (cadr pl1-p3))
          (list 10 (car pl1-p4) (cadr pl1-p4)))
        (list strut-xdata)
      )
    )

    (entmake
      (append
        (list
          '(0 . "LWPOLYLINE")
          '(100 . "AcDbEntity")
          '(100 . "AcDbPolyline")
          '(8 . "_버팀보(Strut)")
          '(62 . 3)
          '(90 . 4)
          '(70 . 1)
          (list 10 (car pl2-p1) (cadr pl2-p1))
          (list 10 (car pl2-p2) (cadr pl2-p2))
          (list 10 (car pl2-p3) (cadr pl2-p3))
          (list 10 (car pl2-p4) (cadr pl2-p4)))
        (list strut-xdata)
      )
    )

    ;; 점선(Web)
    (setq p1-in (polar pt-beam-start pt-dir half-tw)
          p2-in (polar pt-beam-end pt-dir half-tw))
    (setq p3-in (polar pt-beam-start (- pt-dir pi) half-tw)
          p4-in (polar pt-beam-end (- pt-dir pi) half-tw))

    (entmake
      (append
        (list
          '(0 . "LWPOLYLINE")
          '(100 . "AcDbEntity")
          '(100 . "AcDbPolyline")
          '(8 . "_버팀보(Strut)")
          '(62 . 1)
          '(6 . "DASHED")
          (cons 48
                (* (if (and (boundp '*tsp-scale-plan*) *tsp-scale-plan*)
                     *tsp-scale-plan*
                     600.0)
                   (/ 500.0 600.0)
                   (if (= (getvar "MEASUREMENT") 1) (/ 1.0 25.0) 1.0)))
          '(90 . 2)
          '(70 . 0)
          (list 10 (car p1-in) (cadr p1-in))
          (list 10 (car p2-in) (cadr p2-in)))
        (list strut-xdata)
      )
    )

    (entmake
      (append
        (list
          '(0 . "LWPOLYLINE")
          '(100 . "AcDbEntity")
          '(100 . "AcDbPolyline")
          '(8 . "_버팀보(Strut)")
          '(62 . 1)
          '(6 . "DASHED")
          (cons 48
                (* (if (and (boundp '*tsp-scale-plan*) *tsp-scale-plan*)
                     *tsp-scale-plan*
                     600.0)
                   (/ 500.0 600.0)
                   (if (= (getvar "MEASUREMENT") 1) (/ 1.0 25.0) 1.0)))
          '(90 . 2)
          '(70 . 0)
          (list 10 (car p3-in) (cadr p3-in))
          (list 10 (car p4-in) (cadr p4-in)))
        (list strut-xdata)
      )
    )

    ;; 잭(Jack) 삽입
    (if (or (equal jack-type "스크류잭") (equal jack-type "1"))
      (setq jack-block-name "스크류잭")
      (setq jack-block-name "유압잭")
    )

    (entmake
      (list
        '(0 . "INSERT")
        (cons 2 jack-block-name)
        (cons 8 (if (equal jack-block-name "스크류잭") "_스크류잭" "_유압잭"))
        '(62 . 2)
        (cons 10 pt-jack-ins)
        '(41 . 1.0)
        '(42 . 1.0)
        '(43 . 1.0)
        (cons 50 jack-rot))
    )

    (setq sub-idx (1+ sub-idx))
  )

  ;; 4. 보강재(Brace) 및 중간말뚝 N등분 배치 및 작도 로직
  (if s-brace-opt
    (progn
      (setq stiff-enable   (nth 0 s-brace-opt)
            slender-limit (nth 1 s-brace-opt)
            is-manual     (nth 2 s-brace-opt)
            manual-interval (nth 3 s-brace-opt))

      (setq margin (atof (nth 4 s-brace-opt)))
      (setq post-enable (nth 5 s-brace-opt)
            post-layout (nth 6 s-brace-opt)
            post-invert (nth 7 s-brace-opt)
            post-side   (nth 8 s-brace-opt))

      (setq total-L (/ strut-len 1000.0))
      (setq L-max (tsp-calc-unsupported-length strut-vals (if (= slender-limit "0") 100.0 120.0)))

      (setq offsets '())

      ;; 세장비를 초과하거나 수동 간격이 켜져있을 때만 등분 계산 수행
      ;; 작도될 때마다 현재 버팀보의 실제 길이를 전역 변수에 저장하여 DCL로 전달
      (setq *tsp-last-strut-len* strut-len)

      (if (or (> total-L L-max) (= is-manual "1"))
        (progn
          (if (= is-manual "1")
            (progn
              (setq interval (* (atof manual-interval) 1000.0))
              (if (> interval 0.01)
                (progn
                  (setq num-div (fix (/ strut-len interval))
                        i 1)
                  (while (<= i num-div)
                    (setq offsets (append offsets (list (* i interval))))
                    (setq i (1+ i))
                  )
                )
              )
            )
            (progn
              (setq num-div (fix (+ (/ total-L L-max) 0.9999))
                    interval (/ strut-len num-div)
                    i 1)

              ;; 자동 계산된 간격 값을 전역 변수에 저장하여 DCL 입력칸에 자동 표기
              (setq *tsp-last-calc-interval* (/ interval 1000.0))

              (while (< i num-div)
                (setq offsets (append offsets (list (* i interval))))
                (setq i (1+ i))
              )
            )
          )
        )
      )

      (if (> (length offsets) 0)
        (progn
          (setq spatial-idx 0)
          (setq post-block (create-post-pile-block h b tw tf))

          ;; 보강재 선 길이 산출 (절반 폭 + 여유장)
          (setq brace-len (+ strut-sys-half-width margin))

          (foreach off offsets
            (setq p-center (polar pt1 strut-ang off))

            ;; 수직 보강재(Brace) H형강 풀스펙(외곽선+점선) 작도
            ;; 메인 버팀보 기준 분할 작도 (Trim 효과 및 2H 중앙 간극 처리 적용)
            (if (= stiff-enable "1")
              (progn
                (setq p-brace-1 (polar p-center (+ strut-ang (/ pi 2.0)) brace-len))
                (setq p-brace-2 (polar p-center (- strut-ang (/ pi 2.0)) brace-len))

                ;; 메인 버팀보에 가려지는 영역을 제외한 시작점(Inner) 산출
                (setq p-brace-1-inner (polar p-center (+ strut-ang (/ pi 2.0)) strut-sys-half-width))
                (setq p-brace-2-inner (polar p-center (- strut-ang (/ pi 2.0)) strut-sys-half-width))

                ;; 1. 외곽선(Flange) 작도 (좌우 마감선 2개 + 상하 플랜지선 2개)
                (setq f1-1 (polar p-brace-1 strut-ang half-b))
                (setq f1-2 (polar p-brace-1-inner strut-ang half-b))
                (setq f1-3 (polar p-brace-1-inner (+ strut-ang pi) half-b))
                (setq f1-4 (polar p-brace-1 (+ strut-ang pi) half-b))

                ;; [수정] 상/하부 플랜지 선 (내측 마감선 제거)
                (entmake (append (list '(0 . "LWPOLYLINE") '(100 . "AcDbEntity") '(100 . "AcDbPolyline") '(8 . "_보강재(Brace)") '(62 . 256) '(90 . 2) '(70 . 0) (list 10 (car f1-1) (cadr f1-1)) (list 10 (car f1-4) (cadr f1-4))) (list strut-xdata)))
                (entmake (append (list '(0 . "LWPOLYLINE") '(100 . "AcDbEntity") '(100 . "AcDbPolyline") '(8 . "_보강재(Brace)") '(62 . 256) '(90 . 2) '(70 . 0) (list 10 (car f1-2) (cadr f1-2)) (list 10 (car f1-3) (cadr f1-3))) (list strut-xdata)))
                
                ;; [추가] 양 끝단 마감선만 2개 생성
                (entmake (append (list '(0 . "LWPOLYLINE") '(100 . "AcDbEntity") '(100 . "AcDbPolyline") '(8 . "_보강재(Brace)") '(62 . 256) '(90 . 2) '(70 . 0) (list 10 (car f1-1) (cadr f1-1)) (list 10 (car f1-2) (cadr f1-2))) (list strut-xdata)))
                (entmake (append (list '(0 . "LWPOLYLINE") '(100 . "AcDbEntity") '(100 . "AcDbPolyline") '(8 . "_보강재(Brace)") '(62 . 256) '(90 . 2) '(70 . 0) (list 10 (car f1-4) (cadr f1-4)) (list 10 (car f1-3) (cadr f1-3))) (list strut-xdata)))

                ;; 방향 2도 동일하게 상/하부 플랜지 선 + 양 끝 마감선 2개로 처리
                (setq f2-1 (polar p-brace-2-inner strut-ang half-b))
                (setq f2-2 (polar p-brace-2 strut-ang half-b))
                (setq f2-3 (polar p-brace-2 (+ strut-ang pi) half-b))
                (setq f2-4 (polar p-brace-2-inner (+ strut-ang pi) half-b))

                (entmake (append (list '(0 . "LWPOLYLINE") '(100 . "AcDbEntity") '(100 . "AcDbPolyline") '(8 . "_보강재(Brace)") '(62 . 256) '(90 . 2) '(70 . 0) (list 10 (car f2-1) (cadr f2-1)) (list 10 (car f2-4) (cadr f2-4))) (list strut-xdata)))
                (entmake (append (list '(0 . "LWPOLYLINE") '(100 . "AcDbEntity") '(100 . "AcDbPolyline") '(8 . "_보강재(Brace)") '(62 . 256) '(90 . 2) '(70 . 0) (list 10 (car f2-2) (cadr f2-2)) (list 10 (car f2-3) (cadr f2-3))) (list strut-xdata)))
                (entmake (append (list '(0 . "LWPOLYLINE") '(100 . "AcDbEntity") '(100 . "AcDbPolyline") '(8 . "_보강재(Brace)") '(62 . 256) '(90 . 2) '(70 . 0) (list 10 (car f2-1) (cadr f2-1)) (list 10 (car f2-2) (cadr f2-2))) (list strut-xdata)))
                (entmake (append (list '(0 . "LWPOLYLINE") '(100 . "AcDbEntity") '(100 . "AcDbPolyline") '(8 . "_보강재(Brace)") '(62 . 256) '(90 . 2) '(70 . 0) (list 10 (car f2-4) (cadr f2-4)) (list 10 (car f2-3) (cadr f2-3))) (list strut-xdata)))

                ;; 2. 웹(Web) 점선
                ;; 방향 1
                (setq w1-1 (polar p-brace-1 strut-ang half-tw))
                (setq w1-2 (polar p-brace-1-inner strut-ang half-tw))
                (setq w1-3 (polar p-brace-1 (+ strut-ang pi) half-tw))
                (setq w1-4 (polar p-brace-1-inner (+ strut-ang pi) half-tw))

                (entmake
                  (append
                    (list
                      '(0 . "LWPOLYLINE")
                      '(100 . "AcDbEntity")
                      '(100 . "AcDbPolyline")
                      '(8 . "_보강재(Brace)")
                      '(62 . 1)
                      '(6 . "DASHED")
                      (cons 48
                            (* (if (and (boundp '*tsp-scale-plan*) *tsp-scale-plan*)
                                 *tsp-scale-plan*
                                 600.0)
                               (/ 500.0 600.0)))
                      '(90 . 2)
                      '(70 . 0)
                      (list 10 (car w1-1) (cadr w1-1))
                      (list 10 (car w1-2) (cadr w1-2)))
                    (list strut-xdata)
                  )
                )

                (entmake
                  (append
                    (list
                      '(0 . "LWPOLYLINE")
                      '(100 . "AcDbEntity")
                      '(100 . "AcDbPolyline")
                      '(8 . "_보강재(Brace)")
                      '(62 . 1)
                      '(6 . "DASHED")
                      (cons 48
                            (* (if (and (boundp '*tsp-scale-plan*) *tsp-scale-plan*)
                                 *tsp-scale-plan*
                                 600.0)
                               (/ 500.0 600.0)))
                      '(90 . 2)
                      '(70 . 0)
                      (list 10 (car w1-3) (cadr w1-3))
                      (list 10 (car w1-4) (cadr w1-4)))
                    (list strut-xdata)
                  )
                )

                ;; 방향 2
                (setq w2-1 (polar p-brace-2-inner strut-ang half-tw))
                (setq w2-2 (polar p-brace-2 strut-ang half-tw))
                (setq w2-3 (polar p-brace-2-inner (+ strut-ang pi) half-tw))
                (setq w2-4 (polar p-brace-2 (+ strut-ang pi) half-tw))

                (entmake
                  (append
                    (list
                      '(0 . "LWPOLYLINE")
                      '(100 . "AcDbEntity")
                      '(100 . "AcDbPolyline")
                      '(8 . "_보강재(Brace)")
                      '(62 . 1)
                      '(6 . "DASHED")
                      (cons 48
                            (* (if (and (boundp '*tsp-scale-plan*) *tsp-scale-plan*)
                                 *tsp-scale-plan*
                                 600.0)
                               (/ 500.0 600.0)))
                      '(90 . 2)
                      '(70 . 0)
                      (list 10 (car w2-1) (cadr w2-1))
                      (list 10 (car w2-2) (cadr w2-2)))
                    (list strut-xdata)
                  )
                )

                (entmake
                  (append
                    (list
                      '(0 . "LWPOLYLINE")
                      '(100 . "AcDbEntity")
                      '(100 . "AcDbPolyline")
                      '(8 . "_보강재(Brace)")
                      '(62 . 1)
                      '(6 . "DASHED")
                      (cons 48
                            (* (if (and (boundp '*tsp-scale-plan*) *tsp-scale-plan*)
                                 *tsp-scale-plan*
                                 600.0)
                               (/ 500.0 600.0)))
                      '(90 . 2)
                      '(70 . 0)
                      (list 10 (car w2-3) (cadr w2-3))
                      (list 10 (car w2-4) (cadr w2-4)))
                    (list strut-xdata)
                  )
                )

                ;; 3. 맞버팀대(2H)일 경우 중앙 간극(Gap)에 중간 보강재 추가 작도
                (if is-double
                  (progn
                    ;; TSP_LISP_BRACE + "MID_GAP" 태그로 작도 → orphan 삭제 루프에서 정상 삭제됨
                    (if (not (tblsearch "APPID" "TSP_LISP_BRACE")) (regapp "TSP_LISP_BRACE"))
                    (setq mid-gap-xdata
                      (list -3
                        (list "TSP_LISP_BRACE"
                          (cons 1070 seg-id)
                          (cons 1040 0.0)
                          (cons 1010 '(0.0 0.0 0.0))
                          (cons 1010 '(0.0 0.0 0.0))
                          (cons 1040 (float h))
                          (cons 1040 (float tw))
                          (cons 1040 (float tf))
                          (cons 1000 "MID_GAP")
                          (cons 1000 boundary-handle)
                        )
                      )
                    )

                    (setq p-mid-1 (polar p-center (+ strut-ang (/ pi 2.0)) half-b))
                    (setq p-mid-2 (polar p-center (- strut-ang (/ pi 2.0)) half-b))

                    ;; 중앙 간극 외곽선(Flange) - 마감선(캡) 아예 없이 평행한 두 선만 작도
                    (setq fm-1 (polar p-mid-1 strut-ang half-b))
                    (setq fm-2 (polar p-mid-2 strut-ang half-b))
                    (setq fm-3 (polar p-mid-2 (+ strut-ang pi) half-b))
                    (setq fm-4 (polar p-mid-1 (+ strut-ang pi) half-b))

                    (entmake (append (list '(0 . "LWPOLYLINE") '(100 . "AcDbEntity") '(100 . "AcDbPolyline") '(8 . "_보강재(Brace)") '(62 . 256) '(90 . 2) '(70 . 0) (list 10 (car fm-1) (cadr fm-1)) (list 10 (car fm-2) (cadr fm-2))) (list mid-gap-xdata)))
                    (entmake (append (list '(0 . "LWPOLYLINE") '(100 . "AcDbEntity") '(100 . "AcDbPolyline") '(8 . "_보강재(Brace)") '(62 . 256) '(90 . 2) '(70 . 0) (list 10 (car fm-4) (cadr fm-4)) (list 10 (car fm-3) (cadr fm-3))) (list mid-gap-xdata)))
                  )
                )
              )
            )

            ;; 중간말뚝 교차(지그재그) 배치 검사
            (setq is-valid-post T)
            (if (and (= post-enable "1") (= post-layout "1"))
              (progn
                (setq invert-val (if (= post-invert "1") 1 0))
                (if (/= (rem (+ spatial-idx invert-val) 2) 0)
                  (setq is-valid-post nil)
                )
              )
            )

            ;; 중간말뚝 작도 및 파고드는 현상(Overlap) 보정
            (if (and (= post-enable "1") is-valid-post)
              (progn
                ;; [1단계] 기본 형태인 왼쪽(L) 기준으로 1H/2H 고유 좌표 및 회전각 산출
                (if is-double
                  (progn
                    ;; 2H: 왼쪽 측면 밀착
                    (setq pt-post-ins (polar p-center (- pt-dir (/ pi 2.0)) half-b))
                    (setq post-rot (+ pt-dir pi))
                  )
                  (progn
                    ;; 1H: 왼쪽 보강재 외곽선과 수동 버팀보 내측면의 교차점을 통한 역산
                    (setq stiff-left-p1 (polar p-center (- pt-dir (/ pi 2.0)) half-b))
                    (setq stiff-left-p2 (polar (polar p-center pt-dir 100.0) (- pt-dir (/ pi 2.0)) half-b))
                    (setq cs-norm1 (+ strut-ang (/ pi 2.0)))
                    (setq cs-norm2 (- strut-ang (/ pi 2.0)))
                    (setq cp1 (polar p-center cs-norm1 strut-sys-half-width))
                    (setq cp2 (polar p-center cs-norm2 strut-sys-half-width))
                    (setq cs-inner-pt (if (< (distance cp1 p-center) (distance cp2 p-center)) cp1 cp2))
                    (setq cs-inner-p2 (polar cs-inner-pt strut-ang 100.0))
                    (setq pt-target (inters stiff-left-p1 stiff-left-p2 cs-inner-pt cs_inner-p2 nil))
                    (setq post-rot (+ strut-ang (/ pi 2.0)))
                    (if pt-target
                      (setq pt-post-ins (polar pt-target post-rot (/ h 2.0)))
                      (setq pt-post-ins p-center) ;; 교차점 도출 실패 시 보험용
                    )
                  )
                )

                ;; [2단계] 스케일 설정
                (setq y_scale 1.0)

                ;; [3단계] 사용자 옵션 오른쪽(R) 선택 시에만 기하학적 대칭 적용
                (if (= post-side "R")
                  (progn
                    (setq post-rot (- (* 2.0 pt-dir) post-rot))
                    (setq dist-to-ins (distance p-center pt-post-ins))
                    (setq ang-to-ins (angle p-center pt-post-ins))
                    (setq mirror-ang (- (* 2.0 pt-dir) ang-to-ins))
                    (setq pt-post-ins (polar p-center mirror-ang dist-to-ins))
                    (setq y_scale -1.0)
                  )
                )

                (entmake
                  (list
                    '(0 . "INSERT")
                    (cons 2 post-block)
                    (cons 8 "_중간말뚝(Post pile)")
                    (cons 62 256)
                    (cons 10 pt-post-ins)
                    '(41 . 1.0)
                    (cons 42 y_scale)
                    '(43 . 1.0)
                    (cons 50 post-rot)))
              )
            )

            (setq spatial-idx (1+ spatial-idx))
          )
        )
      )
    )
  )

  ;; 5. 방금 새로 그려진 객체들의 ID를 수집하여 반환
  (setq new-ents '())
  (setq nxt start-ent)

  (while (setq nxt (entnext nxt))
    (setq new-ents (append new-ents (list nxt)))
  )

  (princ "\n[성공] 버팀보 작도 및 중간말뚝 배치가 완료되었습니다.")
  new-ents
)



;;;;==========================================================================
;;;; defun tsp-draw-realtime-continuous-braces : 순수 좌표 추적 기반 연속 보강재 실시간 분할 작도 함수
;;;;==========================================================================
(defun tsp-draw-realtime-continuous-braces (pts-list s-brace-opt sec-str is-double strut-ang strut-len seg-id / boundary-handle stiff-enable slender-limit is-manual manual-interval margin strut-vals h b tw tf half-b half-tw strut-sys-half-width brace-xdata mid-gap-xdata brace-ents total-L L-max offsets interval num-div i draw-segs mid-gap-segs num-pts idx cur-pt p-center p-left p-right p-start p-mid-left p-mid-right next-pt p-next-center p-next-left p-end pA pB f1-1 f1-2 f2-1 f2-2 w1-1 w1-2 w2-1 w2-2)
  (setq stiff-enable (nth 0 s-brace-opt) slender-limit (nth 1 s-brace-opt) is-manual (nth 2 s-brace-opt) manual-interval (nth 3 s-brace-opt) margin (atof (nth 4 s-brace-opt)))
  (if (/= stiff-enable "1") (exit))
  (setq boundary-handle (tsp-get-entity-handle *tsp-boundary-ent*))

  (create-layer-if-not-exists "_보강재(Brace)" "7")
  (if (not (tblsearch "LTYPE" "DASHED")) (vl-catch-all-apply 'vla-load (list (vla-get-linetypes (vla-get-activedocument (vlax-get-acad-object))) "DASHED" (if (= (getvar "MEASUREMENT") 1) "acadiso.lin" "acad.lin"))))

  ;; 1. 제원 파싱 및 단면 치수 정의
  (setq strut-vals (parse-h-spec (if (wcmatch sec-str "2H *") (vl-string-subst "" "2H " sec-str) sec-str)))
  (if (null strut-vals) (setq strut-vals '(300 300 10 15)))
  (setq h (float (nth 0 strut-vals)) b (float (nth 1 strut-vals)) tw (float (nth 2 strut-vals)) tf (float (nth 3 strut-vals)))
  (setq half-b (/ b 2.0) half-tw (/ tw 2.0))
  (setq strut-sys-half-width (if is-double (* b 1.5) (/ b 2.0)))

  ;; ARX 크래시 방지를 위해 LISP 전용 APPID 부여 (0.0 좌표 벡터 계산/분모 오류 완벽 차단)
  (if (not (tblsearch "APPID" "TSP_LISP_BRACE")) (regapp "TSP_LISP_BRACE"))
  (setq brace-xdata 
    (list -3 
      (list "TSP_LISP_BRACE" 
        (cons 1070 seg-id) 
        (cons 1040 0.0) 
        (cons 1010 '(0.0 0.0 0.0)) 
        (cons 1010 '(0.0 0.0 0.0))
        (cons 1040 (float h))
        (cons 1040 (float tw))
        (cons 1040 (float tf))
        (cons 1000 "CONT_BRACE")
        (cons 1000 boundary-handle)
      )
    )
  )
  ;; [버그B수정] 맞버팀대 중앙 간극 선분 전용 XDATA: MID_GAP 태그로 수동추가 교차점 검색에서 제외
  (setq mid-gap-xdata
    (list -3
      (list "TSP_LISP_BRACE"
        (cons 1070 seg-id)
        (cons 1040 0.0)
        (cons 1010 '(0.0 0.0 0.0))
        (cons 1010 '(0.0 0.0 0.0))
        (cons 1040 (float h))
        (cons 1040 (float tw))
        (cons 1040 (float tf))
        (cons 1000 "MID_GAP")
        (cons 1000 boundary-handle)
      )
    )
 )

  (setq brace-ents '())
  (if (> (length pts-list) 0)
    (progn
      ;; 2. 실시간 입력된 순수 좌표들을 배열 축 방향으로 기하학적 정렬
      (setq pts-list (vl-sort pts-list
        '(lambda (p1 p2)
           (< (tsp-project-dist (car pts-list) (+ strut-ang (/ pi 2.0)) p1)
              (tsp-project-dist (car pts-list) (+ strut-ang (/ pi 2.0)) p2))
         )
      ))

      ;; 3. 세장비 한계에 따른 등분선 오프셋 산출
      (setq total-L (/ strut-len 1000.0))
      (setq L-max (tsp-calc-unsupported-length strut-vals (if (= slender-limit "0") 100.0 120.0)))
      (setq offsets '())

      (if (or (> total-L L-max) (= is-manual "1"))
        (if (= is-manual "1")
          (progn
            (setq interval (* (atof manual-interval) 1000.0))
            (if (> interval 0.01)
              (progn
                (setq num-div (fix (/ strut-len interval)) i 1)
                (while (<= i num-div)
                  (setq offsets (append offsets (list (* i interval))))
                  (setq i (1+ i))
                )
              )
            )
          )
          (progn
            (setq num-div (fix (+ (/ total-L L-max) 0.9999)) interval (/ strut-len num-div) i 1)
            (while (< i num-div)
              (setq offsets (append offsets (list (* i interval))))
              (setq i (1+ i))
            )
          )
        )
      )

      ;; 4. 등분 분할선마다 전체 버팀보 배열을 관통하는 최적화 선분 수집
      (foreach off offsets
        (setq draw-segs '())
        (setq mid-gap-segs '())
        (setq num-pts (length pts-list))
        (setq idx 0)

        (while (< idx num-pts)
          (setq cur-pt (nth idx pts-list))
          (setq p-center (polar cur-pt strut-ang off))
          (setq p-left (polar p-center (- strut-ang (/ pi 2.0)) strut-sys-half-width))
          (setq p-right (polar p-center (+ strut-ang (/ pi 2.0)) strut-sys-half-width))

          ;; 4-1. [수정] 오직 전체 배열의 맨 첫 번째(idx=0) 왼쪽 끝에만 여유장 구간 배치
          (if (= idx 0)
            (progn
              (setq p-start (polar p-left (- strut-ang (/ pi 2.0)) margin))
              (setq draw-segs (append draw-segs (list (cons p-start p-left))))
            )
          )

          ;; 4-2. 맞버팀대(2H) 내부 중앙 간극 공간 자동 트림 복원
          ;; [버그B수정] 중앙 간극 선분은 draw-segs(CONT_BRACE)가 아닌 mid-gap-segs(MID_GAP)로 분리
          ;; -> tsp-manual-add-post 에서 MID_GAP 태그를 확인하여 교차점 검색 제외
          (if is-double
            (progn
              (setq p-mid-left (polar p-center (- strut-ang (/ pi 2.0)) half-b))
              (setq p-mid-right (polar p-center (+ strut-ang (/ pi 2.0)) half-b))
              (setq mid-gap-segs (append mid-gap-segs (list (cons p-mid-left p-mid-right))))
            )
          )

          ;; 4-3. 현재 버팀보 우측 경계면에서 다음 버팀보 좌측 경계면까지 연속 띠장선 연결
          (if (< idx (1- num-pts))
            (progn
              (setq next-pt (nth (1+ idx) pts-list))
              (setq p-next-center (polar next-pt strut-ang off))
              (setq p-next-left (polar p-next-center (- strut-ang (/ pi 2.0)) strut-sys-half-width))
              (setq draw-segs (append draw-segs (list (cons p-right p-next-left))))
            )
          )

          ;; 4-4. [수정] 오직 전체 배열의 맨 마지막 우측 끝에만 여유장 구간 배치
          (if (= idx (1- num-pts))
            (progn
              (setq p-end (polar p-right (+ strut-ang (/ pi 2.0)) margin))
              (setq draw-segs (append draw-segs (list (cons p-right p-end))))
            )
          )

          (setq idx (1+ idx))
        )

        ;; 5. 가상 트림이 완료된 빈 공간 세그먼트들에만 물리 객체 작도 (XDATA 결합)
        (setq num-draw-segs (length draw-segs))
        (setq seg-idx 0)
        (foreach seg draw-segs
          (setq pA (car seg) pB (cdr seg))
          (if (> (distance pA pB) 0.1)
            (progn
              (setq seg-ang (angle pA pB))
              ;; 플랜지 선 1 (pA~pB의 +half-b 방향, 보강재 진행방향 수직)
              (setq f1-1 (polar pA (+ seg-ang (/ pi 2.0)) half-b))
              (setq f1-2 (polar pB (+ seg-ang (/ pi 2.0)) half-b))
              (entmake (append (list '(0 . "LWPOLYLINE") '(100 . "AcDbEntity") '(100 . "AcDbPolyline") '(8 . "_보강재(Brace)") '(62 . 256) '(90 . 2) '(70 . 0)
                             (list 10 (car f1-1) (cadr f1-1)) (list 10 (car f1-2) (cadr f1-2)))
                             (list brace-xdata)))
              (setq brace-ents (append brace-ents (list (entlast))))
              ;; 플랜지 선 2 (pA~pB의 -half-b 방향)
              (setq f2-1 (polar pA (- seg-ang (/ pi 2.0)) half-b))
              (setq f2-2 (polar pB (- seg-ang (/ pi 2.0)) half-b))
              (entmake (append (list '(0 . "LWPOLYLINE") '(100 . "AcDbEntity") '(100 . "AcDbPolyline") '(8 . "_보강재(Brace)") '(62 . 256) '(90 . 2) '(70 . 0)
                             (list 10 (car f2-1) (cadr f2-1)) (list 10 (car f2-2) (cadr f2-2)))
                             (list brace-xdata)))
              (setq brace-ents (append brace-ents (list (entlast))))
              ;; 끝면 연결선 - pA측 캡 (f1-1 ~ f2-1): 맨 처음 세그먼트에만 작도
              (if (= seg-idx 0)
                (progn
                  (entmake (append (list '(0 . "LWPOLYLINE") '(100 . "AcDbEntity") '(100 . "AcDbPolyline") '(8 . "_보강재(Brace)") '(62 . 256) '(90 . 2) '(70 . 0)
                                 (list 10 (car f1-1) (cadr f1-1)) (list 10 (car f2-1) (cadr f2-1)))
                                  (list brace-xdata)))
                  (setq brace-ents (append brace-ents (list (entlast))))
                )
              )
              ;; 끝면 연결선 - pB측 캡 (f1-2 ~ f2-2): 맨 마지막 세그먼트에만 작도
              (if (= seg-idx (1- num-draw-segs))
                (progn
                  (entmake (append (list '(0 . "LWPOLYLINE") '(100 . "AcDbEntity") '(100 . "AcDbPolyline") '(8 . "_보강재(Brace)") '(62 . 256) '(90 . 2) '(70 . 0)
                                 (list 10 (car f1-2) (cadr f1-2)) (list 10 (car f2-2) (cadr f2-2)))
                                  (list brace-xdata)))
                  (setq brace-ents (append brace-ents (list (entlast))))
                )
              )
              ;; 웹 파선 1 (+half-tw)
              (setq w1-1 (polar pA (+ seg-ang (/ pi 2.0)) half-tw))
              (setq w1-2 (polar pB (+ seg-ang (/ pi 2.0)) half-tw))
              (entmake (append (list '(0 . "LWPOLYLINE") '(100 . "AcDbEntity") '(100 . "AcDbPolyline") '(8 . "_보강재(Brace)") '(62 . 1) '(6 . "DASHED") 
                                     (cons 48 (* (if (and (boundp '*tsp-scale-plan*) *tsp-scale-plan*) *tsp-scale-plan* 600.0) (/ 500.0 600.0) (if (= (getvar "MEASUREMENT") 1) (/ 1.0 25.0) 1.0)))
                                     '(90 . 2) '(70 . 0)
                             (list 10 (car w1-1) (cadr w1-1)) (list 10 (car w1-2) (cadr w1-2)))
                             (list brace-xdata)))
              (setq brace-ents (append brace-ents (list (entlast))))
              ;; 웹 파선 2 (-half-tw)
              (setq w2-1 (polar pA (- seg-ang (/ pi 2.0)) half-tw))
              (setq w2-2 (polar pB (- seg-ang (/ pi 2.0)) half-tw))
              (entmake (append (list '(0 . "LWPOLYLINE") '(100 . "AcDbEntity") '(100 . "AcDbPolyline") '(8 . "_보강재(Brace)") '(62 . 1) '(6 . "DASHED") 
                                     (cons 48 (* (if (and (boundp '*tsp-scale-plan*) *tsp-scale-plan*) *tsp-scale-plan* 600.0) (/ 500.0 600.0) (if (= (getvar "MEASUREMENT") 1) (/ 1.0 25.0) 1.0)))
                                     '(90 . 2) '(70 . 0)
                             (list 10 (car w2-1) (cadr w2-1)) (list 10 (car w2-2) (cadr w2-2)))
                             (list brace-xdata)))
              (setq brace-ents (append brace-ents (list (entlast))))
            )
          )
          (setq seg-idx (1+ seg-idx))
        )

        ;; 6. 맞버팀대 중앙 간극 선분 별도 작도 (MID_GAP XDATA로 교차점 검색에서 제외)
        ;; 동일한 _보강재(Brace) 레이어에 그려져 시각적으로 동일하지만 tsp-manual-add-post가 건너뜀
        ;; 플랜지를 4점 직사각형 대신 2선(흰색 실선)으로 작도
        (foreach seg mid-gap-segs
          (setq pA (car seg) pB (cdr seg))
          (if (> (distance pA pB) 0.1)
            (progn
              ;; mid-gap도 pA->pB 방향(seg-ang) 기준으로 수직 오프셋
              (setq seg-ang (angle pA pB))
              ;; 플랜지 선 1 (+half-b)
              (setq f1-1 (polar pA (+ seg-ang (/ pi 2.0)) half-b))
              (setq f1-2 (polar pB (+ seg-ang (/ pi 2.0)) half-b))
              (entmake (append (list '(0 . "LWPOLYLINE") '(100 . "AcDbEntity") '(100 . "AcDbPolyline") '(8 . "_보강재(Brace)") '(62 . 256) '(90 . 2) '(70 . 0)
                             (list 10 (car f1-1) (cadr f1-1)) (list 10 (car f1-2) (cadr f1-2)))
                             (list mid-gap-xdata)))
              (setq brace-ents (append brace-ents (list (entlast))))
              ;; 플랜지 선 2 (-half-b)
              (setq f2-1 (polar pA (- seg-ang (/ pi 2.0)) half-b))
              (setq f2-2 (polar pB (- seg-ang (/ pi 2.0)) half-b))
              (entmake (append (list '(0 . "LWPOLYLINE") '(100 . "AcDbEntity") '(100 . "AcDbPolyline") '(8 . "_보강재(Brace)") '(62 . 256) '(90 . 2) '(70 . 0)
                             (list 10 (car f2-1) (cadr f2-1)) (list 10 (car f2-2) (cadr f2-2)))
                             (list mid-gap-xdata)))
              (setq brace-ents (append brace-ents (list (entlast))))
              ;; 웹 파선 1 (+half-tw)
              (setq w1-1 (polar pA (+ seg-ang (/ pi 2.0)) half-tw))
              (setq w1-2 (polar pB (+ seg-ang (/ pi 2.0)) half-tw))
              (entmake (append (list '(0 . "LWPOLYLINE") '(100 . "AcDbEntity") '(100 . "AcDbPolyline") '(8 . "_보강재(Brace)") '(62 . 1) '(6 . "DASHED") 
                                     (cons 48 (* (if (and (boundp '*tsp-scale-plan*) *tsp-scale-plan*) *tsp-scale-plan* 600.0) (/ 500.0 600.0) (if (= (getvar "MEASUREMENT") 1) (/ 1.0 25.0) 1.0)))
                                     '(90 . 2) '(70 . 0)
                             (list 10 (car w1-1) (cadr w1-1)) (list 10 (car w1-2) (cadr w1-2)))
                             (list mid-gap-xdata)))
              (setq brace-ents (append brace-ents (list (entlast))))
              ;; 웹 파선 2 (-half-tw)
              (setq w2-1 (polar pA (- seg-ang (/ pi 2.0)) half-tw))
              (setq w2-2 (polar pB (- seg-ang (/ pi 2.0)) half-tw))
              (entmake (append (list '(0 . "LWPOLYLINE") '(100 . "AcDbEntity") '(100 . "AcDbPolyline") '(8 . "_보강재(Brace)") '(62 . 1) '(6 . "DASHED") 
                                     (cons 48 (* (if (and (boundp '*tsp-scale-plan*) *tsp-scale-plan*) *tsp-scale-plan* 600.0) (/ 500.0 600.0) (if (= (getvar "MEASUREMENT") 1) (/ 1.0 25.0) 1.0)))
                                     '(90 . 2) '(70 . 0)
                             (list 10 (car w2-1) (cadr w2-1)) (list 10 (car w2-2) (cadr w2-2)))
                             (list mid-gap-xdata)))
              (setq brace-ents (append brace-ents (list (entlast))))
            )
          )
        )
      )
    )
  )
  brace-ents
)


;;;;==========================================================================
;;;; defun tsp-manual-add-post : 중간말뚝 수동추가
;;;;==========================================================================
(defun tsp-manual-add-post (active-seg-id / old-osmode pt p-center chk_p1 chk_p2 ss-cross p1_box p2_box ss i ent ent-data p1 p2 min-dist line-ang perp-dist best-p1 best-p2 stiff-dir sum-x sum-y count centroid vec_dir vec_c2p cross_z dot_z rot ins_pt post-block added-list session-ents last-act loop custom-h custom-b custom-tw custom-tf target-seg-id ss-all-struts valid-strut-found j e-data xdata x-vals t-p1 t-p2 t-p3 post-data-record check-id first-run pure-b cur-layer s-p1 s-p2 s-width s-ang d-proj d-perp y_scale brace-xd brace-ang-ok bx-vals pt-cnt tmp-pa tmp-pb tmp-ang ang-diff)
  (setq old-osmode (getvar "OSMODE"))
  (setvar "OSMODE" 32)
  
  (if active-seg-id
    (princ (strcat "\n[안내] Seg-" (itoa active-seg-id) " 수동 추가 작업을 시작합니다."))
    (princ "\n[안내] 중간말뚝 수동 추가 작업을 시작합니다. (원하는 버팀보 영역을 클릭하세요)")
  )
  (setq session-ents '() loop T first-run T)
  
  (while loop
    (initget "Undo")
    (setq pt (vl-catch-all-apply 'getpoint (list "\n[수동 추가] 중간말뚝을 생성할 교차점 클릭 [명령취소(U)] <종료: Enter/ESC>: ")))
    
    (cond
      ((vl-catch-all-error-p pt)
       (setq loop nil)
       (princ "\n[취소] 사용자가 ESC를 눌러 추가 작업을 중단했습니다.")
      )
      ((= pt "Undo")
       (setq first-run nil)
       (if session-ents
         (progn
           (setq last-act (car session-ents))
           (setq session-ents (cdr session-ents))
           (if (= (type last-act) 'ENAME) (if (entget last-act) (entdel last-act)))
           
           (if *tsp-use-temp-posts*
             (if *tsp-temp-added-posts*
               (setq *tsp-temp-added-posts* (reverse (cdr (reverse *tsp-temp-added-posts*))))
             )
             (progn
               (setq added-list (vlax-ldata-get "TSP_DICT" "ADDED_POSTS"))
               (if added-list
                 (progn
                   (setq added-list (reverse (cdr (reverse added-list))))
                   (vlax-ldata-put "TSP_DICT" "ADDED_POSTS" added-list)
                 )
               )
             )
           )
           (setq *tsp-data-dirty* T)
           (if (and (boundp '*tsp-boundary-ent*) *tsp-boundary-ent* (boundp '*tsp-boundary-orient*) *tsp-boundary-orient*)
             (tsp-redraw-realtime-plan *tsp-boundary-ent* *tsp-boundary-orient*)
             (command "_.REGEN")
           )
           (princ "\n[실행] 직전에 추가한 중간말뚝을 취소(Undo)했습니다.")
         )
         (princ "\n[알림] 취소할 작업 내역이 없습니다.")
       )
      )
      ((not pt)
       (if first-run
         (setq first-run nil)
         (setq loop nil)
       )
      )
      ((listp pt)
       (setq first-run nil)
       (setq p-center (list (car pt) (cadr pt) 0.0))
       
       (setq custom-h 300.0 custom-b 300.0 custom-tw 10.0 custom-tf 15.0 target-seg-id nil)
       (setq ss-all-struts (ssget "X" '((0 . "LWPOLYLINE") (8 . "_사보강재(Corner_Strut),_버팀보(Strut)"))))
       (setq valid-strut-found nil)
       
       (if ss-all-struts
         (progn
           (setq j 0)
           (while (and (< j (sslength ss-all-struts)) (not valid-strut-found))
             (setq e-data (entget (ssname ss-all-struts j) '("TSP_STRUT_SPEC")))
             (setq cur-layer (cdr (assoc 8 e-data)))
             (setq xdata (assoc -3 e-data))
             (if xdata
               (progn
                 (setq x-vals (cdr (car (cdr xdata))))
                 (if (>= (length x-vals) 8)
                   (progn
                     (setq check-id (cdr (nth 0 x-vals)))
                     ;; active-seg-id가 nil이면 ID 검사 패스 (클릭한 영역의 ID를 자동 채택)
                     (if (or (null active-seg-id) (= check-id active-seg-id))
                       (progn
                         (if (= cur-layer "_사보강재(Corner_Strut)")
                           (progn
                             (setq t-p1 (cdr (nth 5 x-vals)))
                             (setq t-p2 (cdr (nth 6 x-vals)))
                             (setq t-p3 (cdr (nth 7 x-vals)))
                             (if (tsp-is-point-in-triangle p-center t-p1 t-p2 t-p3)
                               (progn
                                 (setq valid-strut-found T target-seg-id check-id)
                                 (setq custom-h (cdr (nth 1 x-vals)) custom-b (cdr (nth 2 x-vals)) custom-tw (cdr (nth 3 x-vals)) custom-tf (cdr (nth 4 x-vals)))
                               )
                             )
                           )
                           (progn
                             (setq s-p1 (cdr (nth 2 x-vals)))
                             (setq s-p2 (cdr (nth 3 x-vals)))
                             (setq s-width (cdr (nth 1 x-vals)))
                             (setq s-ang (angle s-p1 s-p2))
                             
                             (setq d-proj (tsp-project-dist s-p1 s-ang p-center))
                             (setq d-perp (abs (- (* (- (car p-center) (car s-p1)) (sin s-ang)) (* (- (cadr p-center) (cadr s-p1)) (cos s-ang)))))
                             
                             (if (and (>= d-proj -10.0) (<= d-proj (+ (distance s-p1 s-p2) 10.0)) (<= d-perp (+ s-width 100.0)))
                               (progn
                                 (setq valid-strut-found T target-seg-id check-id)
                                 (setq pure-b (if (> (length x-vals) 9) (cdr (nth 9 x-vals)) (cdr (nth 4 x-vals))))
                                 (setq custom-h (cdr (nth 4 x-vals)) custom-b pure-b custom-tw (cdr (nth 5 x-vals)) custom-tf (cdr (nth 6 x-vals)))
                               )
                             )
                           )
                         )
                       )
                     )
                   )
                 )
               )
             )
             (setq j (1+ j))
           )
         )
       )

       (if (not valid-strut-found)
         (princ (strcat "\n[오류] 현재 설정 중인 [Seg-" (if active-seg-id (itoa active-seg-id) "?") "]의 구역 내부가 아닙니다. 버팀보 또는 사보강재 영역 내부를 클릭해주세요."))
         (progn
           (setq chk_p1 (list (- (car p-center) 2.0) (- (cadr p-center) 2.0)))
           (setq chk_p2 (list (+ (car p-center) 2.0) (+ (cadr p-center) 2.0)))
           (setq ss-cross (ssget "C" chk_p1 chk_p2 '((0 . "*LINE"))))

           ;; ---------------------------------------------------------------
           ;; [버그B-1 수정] 버팀보(RECT) 영역인 경우
           ;; _버팀보(Strut) 레이어 플랜지 선분을 검색하여
           ;; TRI 경로와 동일한 centroid -> cross_z/dot_z 방식으로 rot/y_scale 결정
           ;; ---------------------------------------------------------------
           (if (and valid-strut-found s-ang s-p1 s-p2)
             ;; --- RECT(버팀보) 경로 ---
             (progn
               (if (and ss-cross (>= (sslength ss-cross) 2))
                 (progn
               ;; [버그B-1 핵심] _버팀보(Strut) 레이어 CONT_BRACE 태그 없는 선분 검색
               ;; -> 플랜지 선분의 centroid와 p-center 방향으로 rot/y_scale 결정
               (setq min-dist 1e99 best-p1 nil best-p2 nil sum-x 0.0 sum-y 0.0 count 0)
               (setq p1_box (list (- (car p-center) 500.0) (- (cadr p-center) 500.0)))
               (setq p2_box (list (+ (car p-center) 500.0) (+ (cadr p-center) 500.0)))
               ;; _버팀보(Strut) 레이어의 LWPOLYLINE 검색 (버팀보 본체 선분)
               (setq ss (ssget "C" p1_box p2_box '((0 . "LWPOLYLINE") (8 . "_버팀보(Strut)"))))
               (if ss
                 (progn
                   (setq i 0)
                   (while (< i (sslength ss))
                     (setq ent (ssname ss i))
                     (setq ent-data (entget ent))
                     ;; XDATA가 없는(보강재 태그 없는) 선분만 사용 - 버팀보 플랜지 외곽선
                     (setq brace-xd (assoc -3 ent-data))
                     (if (not brace-xd)
                       (progn
                         (setq p1 (cdr (assoc 10 ent-data)))
                         (setq p2 nil)
                         (setq pt-cnt 0)
                         (foreach dxf ent-data
                           (if (= (car dxf) 10)
                             (progn
                               (if (= pt-cnt 0) (setq p1 (cdr dxf)))
                               (if (= pt-cnt 1) (setq p2 (cdr dxf)))
                               (setq pt-cnt (1+ pt-cnt))
                             )
                           )
                         )
                         (if (and p1 p2)
                           (progn
                             (setq tmp-ang (angle p1 p2))
                             (setq ang-diff (abs (- tmp-ang s-ang)))
                             (if (> ang-diff pi) (setq ang-diff (- (* 2.0 pi) ang-diff)))
                             ;; 버팀보 방향(s-ang)에 수직인 선분만 플랜지로 채택 (90도+/-20도)
                             (if (or (and (> ang-diff (- (/ pi 2.0) 0.35)) (< ang-diff (+ (/ pi 2.0) 0.35)))
                                     (and (> ang-diff (- (* 1.5 pi) 0.35)) (< ang-diff (+ (* 1.5 pi) 0.35))))
                               (progn
                                 (setq tmp-pa (list (/ (+ (car p1) (car p2)) 2.0) (/ (+ (cadr p1) (cadr p2)) 2.0) 0.0))
                                 (setq perp-dist (distance p-center tmp-pa))
                                 (if (< perp-dist min-dist)
                                   (progn
                                     (setq min-dist perp-dist)
                                     (setq best-p1 p1 best-p2 p2)
                                   )
                                 )
                                 (setq sum-x (+ sum-x (car tmp-pa)) sum-y (+ sum-y (cadr tmp-pa)) count (1+ count))
                               )
                             )
                           )
                         )
                       )
                     )
                     (setq i (1+ i))
                   )
                 )
               )
               ;; centroid 또는 s-p1~s-p2 중심으로 방향 계산
               (if (and best-p1 best-p2 (> count 0))
                 (progn
                   (setq centroid (list (/ sum-x count) (/ sum-y count) 0.0))
                   ;; 플랜지 선분 검색 성공: 그 선분 방향(= 보강재 방향)을 stiff-dir로 사용
                   (setq stiff-dir (angle best-p1 best-p2))
                 )
                 (progn
                   ;; [Fix6] 플랜지 선분 미발견 -> s-p1~s-p2 중심점으로 폴백
                   ;; 폴백 시 stiff-dir = 보강재 방향 = 버팀보(s-ang)에 수직 = s-ang + pi/2
                   (setq centroid (list (/ (+ (car s-p1) (car s-p2)) 2.0)
                                        (/ (+ (cadr s-p1) (cadr s-p2)) 2.0) 0.0))
                   (setq stiff-dir (+ s-ang (/ pi 2.0)))
                 )
               )
               (setq vec_dir (list (cos stiff-dir) (sin stiff-dir)))
               (setq vec_c2p (list (- (car p-center) (car centroid))
                                    (- (cadr p-center) (cadr centroid))))
               (setq cross_z (- (* (car vec_dir) (cadr vec_c2p)) (* (cadr vec_dir) (car vec_c2p))))
               (setq dot_z   (+ (* (car vec_dir) (car vec_c2p)) (* (cadr vec_dir) (cadr vec_c2p))))
               (if (>= dot_z 0.0) (setq rot stiff-dir) (setq rot (+ stiff-dir pi)))
               (if (< (* cross_z dot_z) 0.0) (setq y_scale -1.0) (setq y_scale 1.0))
               (setq ins_pt (polar p-center rot (/ custom-b 2.0)))
               (setq post-block (create-post-pile-block custom-h custom-b custom-tw custom-tf))
               (setq post-data-record (list ins_pt rot y_scale custom-h custom-b custom-tw custom-tf target-seg-id))

               ;; [버그A수정 강화] 삭제 기록 제거: ins_pt 기준 거리 대신 valid-triangles 영역 기반
               ;; -> 같은 구역 내 삭제된 모든 기록 중 ins_pt 근처(500mm) 것을 제거
               (if *tsp-use-temp-posts*
                 (if *tsp-temp-deleted-posts*
                   (setq *tsp-temp-deleted-posts*
                     (vl-remove-if
                       '(lambda (del-pt) (< (distance ins_pt del-pt) 10.0))
                       *tsp-temp-deleted-posts*
                     )
                   )
                 )
                 (progn
                   (setq *tsp-deleted-post-points* (vlax-ldata-get "TSP_DICT" "DELETED_POSTS"))
                   (if *tsp-deleted-post-points*
                     (progn
                       (setq *tsp-deleted-post-points*
                         (vl-remove-if
                           '(lambda (del-pt) (< (distance ins_pt del-pt) 10.0))
                           *tsp-deleted-post-points*
                         )
                       )
                       (vlax-ldata-put "TSP_DICT" "DELETED_POSTS" *tsp-deleted-post-points*)
                     )
                   )
                 )
               )

               (if *tsp-use-temp-posts*
                 (setq *tsp-temp-added-posts* (append *tsp-temp-added-posts* (list post-data-record)))
                 (progn
                   (setq added-list (vlax-ldata-get "TSP_DICT" "ADDED_POSTS"))
                   (if (not added-list) (setq added-list '()))
                   (setq added-list (append added-list (list post-data-record)))
                   (vlax-ldata-put "TSP_DICT" "ADDED_POSTS" added-list)
                 )
               )
               (setq *tsp-data-dirty* T)
               (if (and (boundp '*tsp-boundary-ent*) *tsp-boundary-ent* (boundp '*tsp-boundary-orient*) *tsp-boundary-orient*)
                 (progn
                   (tsp-redraw-realtime-plan *tsp-boundary-ent* *tsp-boundary-orient*)
                   (setq session-ents (cons 'REDRAW session-ents))
                 )
                 (progn
                   (if (not (tblsearch "APPID" "TSP_LISP_POST")) (regapp "TSP_LISP_POST"))
                   (entmake (list '(0 . "INSERT") (cons 2 post-block) (cons 8 "_중간말뚝(Post pile)") (cons 62 256) (cons 10 ins_pt) '(41 . 1.0) (cons 42 y_scale) '(43 . 1.0) (cons 50 rot)
                                  (list -3 (list "TSP_LISP_POST" (cons 1000 "MANUAL_POST")))
                             ))
                   (setq session-ents (cons (entlast) session-ents))
                 )
               )
               (princ "\n[완료] 중간말뚝 추가 완료.")
                 ) ;; end ss-cross true-branch
                 (princ "\n[오류] 두 선이 만나는 정확한 '교차점'이 아닙니다. 스냅을 이용해 다시 클릭하세요.")
               ) ;; end if ss-cross (RECT 경로)
             ) ;; end RECT progn
             ;; --- TRI(사보강재) 경로: 기존 brace 검색 로직 ---
             (progn
           (if (and ss-cross (>= (sslength ss-cross) 2))
             (progn
               (setq min-dist 1e99 best-p1 nil best-p2 nil sum-x 0.0 sum-y 0.0 count 0)
               (setq p1_box (list (- (car p-center) 500.0) (- (cadr p-center) 500.0)))
               (setq p2_box (list (+ (car p-center) 500.0) (+ (cadr p-center) 500.0)))
               ;; [버그B수정] _버팀보(Strut) 레이어 제거 - 버팀보 자체 선분이 잘못 선택되는 문제 방지
               ;; _보강재(Brace) 레이어만 검색하고 XDATA로 연속보강재 식별
               (setq ss (ssget "C" p1_box p2_box '((0 . "LWPOLYLINE") (8 . "_보강재(Brace)"))))
               
               (if ss
                 (progn
                   (setq i 0)
                   (while (< i (sslength ss))
                     (setq ent (ssname ss i))
                     (setq ent-data (entget ent '("TSP_LISP_BRACE")))
                     (setq p1 nil p2 nil)
                     ;; [버그B수정] XDATA가 있는 연속보강재(TSP_LISP_BRACE)인 경우
                     ;; 1단계: MID_GAP 태그 확인 -> 맞버팀대 중앙 간극 선분이면 즉시 제외
                     ;; 2단계: 버팀보 방향(s-ang)과 평행 여부로 수직/사선 선분 추가 배제
                     (setq brace-xd (assoc -3 ent-data))
                     (setq brace-ang-ok T) ;; 기본적으로 통과 (XDATA 없는 일반 보강재)
                     (if brace-xd
                       (progn
                         (setq bx-vals (cdr (car (cdr brace-xd))))
                         ;; [핵심 1단계] MID_GAP 태그 체크: 맞버팀대 중앙 선분은 즉시 제외
                         (if (and (>= (length bx-vals) 8)
                                  (= (cdr (nth 7 bx-vals)) "MID_GAP"))
                           (setq brace-ang-ok nil)
                           (progn
                             ;; [2단계] 각도 평행 검사 (기존 수직선분 제외 로직 유지)
                             (setq pt-cnt 0)
                             (foreach item ent-data
                               (if (and (= (car item) 10) (< pt-cnt 2))
                                 (progn
                                   (if (= pt-cnt 0) (setq tmp-pa (cdr item)) (setq tmp-pb (cdr item)))
                                   (setq pt-cnt (1+ pt-cnt))
                                 )
                               )
                             )
                             (if (and tmp-pa tmp-pb)
                               (progn
                                 (setq tmp-ang (angle (list (car tmp-pa) (cadr tmp-pa) 0.0)
                                                      (list (car tmp-pb) (cadr tmp-pb) 0.0)))
                                 ;; 버팀보 방향(s-ang)과 평행 여부 확인 (허용 오차 15도)
                                 ;; s-ang은 RECT 경로에서만 설정됨, TRI 경로에서는 nil일 수 있으므로 nil 체크
                                 (if s-ang
                                   (progn
                                     (setq ang-diff (abs (- (rem (abs tmp-ang) pi) (rem (abs s-ang) pi))))
                                     (if (> ang-diff (/ pi 2.0)) (setq ang-diff (- pi ang-diff)))
                                     (if (> ang-diff (/ pi 12.0)) (setq brace-ang-ok nil))
                                   )
                                 )
                               )
                             )
                           )
                         )
                       )
                     )
                     (if brace-ang-ok
                       (progn
                         (foreach item ent-data
                           (if (= (car item) 10)
                             (progn
                               (if (null p1) (setq p1 (cdr item)) (if (null p2) (setq p2 (cdr item))))
                               (setq sum-x (+ sum-x (car (cdr item))))
                               (setq sum-y (+ sum-y (cadr (cdr item))))
                               (setq count (1+ count))
                             )
                           )
                         )
                         (if (and p1 p2)
                           (progn
                             (setq p1 (list (car p1) (cadr p1) 0.0))
                             (setq p2 (list (car p2) (cadr p2) 0.0))
                             (setq line-ang (angle p1 p2))
                             (setq perp-dist (abs (- (* (- (car p-center) (car p1)) (sin line-ang)) (* (- (cadr p-center) (cadr p1)) (cos line-ang)))))
                             (if (< perp-dist min-dist)
                               (progn
                                 (setq min-dist perp-dist)
                                 (setq best-p1 p1 best-p2 p2)
                               )
                             )
                           )
                         )
                       )
                     )
                     (setq i (1+ i))
                   )
                   
                   (if (and best-p1 best-p2 (> count 0) (< min-dist 10.0))
                     (progn
                       (setq centroid (list (/ sum-x count) (/ sum-y count) 0.0))
                       (setq stiff-dir (angle best-p1 best-p2))
                       (setq vec_dir (list (cos stiff-dir) (sin stiff-dir)))
                       (setq vec_c2p (list (- (car p-center) (car centroid)) (- (cadr p-center) (cadr centroid))))
                       
                       (setq cross_z (- (* (car vec_dir) (cadr vec_c2p)) (* (cadr vec_dir) (car vec_c2p))))
                       (setq dot_z (+ (* (car vec_dir) (car vec_c2p)) (* (cadr vec_dir) (cadr vec_c2p))))
                       
                       (if (>= dot_z 0.0) (setq rot stiff-dir) (setq rot (+ stiff-dir pi)))
                       (if (< (* cross_z dot_z) 0.0) (setq y_scale -1.0) (setq y_scale 1.0))
                       
                       (setq ins_pt (polar p-center rot (/ custom-b 2.0)))
                       (setq post-block (create-post-pile-block custom-h custom-b custom-tw custom-tf))
                       
                       (setq post-data-record (list ins_pt rot y_scale custom-h custom-b custom-tw custom-tf target-seg-id))
                       
                       ;; [버그A수정 강화] 삭제 기록 제거: ins_pt 기준 500mm 이내 모두 제거
                       (if *tsp-use-temp-posts*
                         (if *tsp-temp-deleted-posts*
                           (setq *tsp-temp-deleted-posts*
                             (vl-remove-if
                               '(lambda (del-pt) (< (distance ins_pt del-pt) 10.0))
                               *tsp-temp-deleted-posts*
                             )
                           )
                         )
                         (progn
                           (setq *tsp-deleted-post-points* (vlax-ldata-get "TSP_DICT" "DELETED_POSTS"))
                           (if *tsp-deleted-post-points*
                             (progn
                               (setq *tsp-deleted-post-points*
                                 (vl-remove-if
                                   '(lambda (del-pt) (< (distance ins_pt del-pt) 10.0))
                                   *tsp-deleted-post-points*
                                 )
                               )
                               (vlax-ldata-put "TSP_DICT" "DELETED_POSTS" *tsp-deleted-post-points*)
                             )
                           )
                         )
                       )

                       (if *tsp-use-temp-posts*
                         (setq *tsp-temp-added-posts* (append *tsp-temp-added-posts* (list post-data-record)))
                         (progn
                           (setq added-list (vlax-ldata-get "TSP_DICT" "ADDED_POSTS"))
                           (if (not added-list) (setq added-list '()))
                           (setq added-list (append added-list (list post-data-record)))
                           (vlax-ldata-put "TSP_DICT" "ADDED_POSTS" added-list)
                         )
                       )
                       
                       (setq *tsp-data-dirty* T)
                       
                       (if (and (boundp '*tsp-boundary-ent*) *tsp-boundary-ent* (boundp '*tsp-boundary-orient*) *tsp-boundary-orient*)
                         (progn
                           (tsp-redraw-realtime-plan *tsp-boundary-ent* *tsp-boundary-orient*)
                           (setq session-ents (cons 'REDRAW session-ents))
                         )
                         (progn
                           ;; [수정] ARX XDATA 규격 충돌 및 크래시 방지를 위해 전용 APPID 사용
                           (if (not (tblsearch "APPID" "TSP_LISP_POST")) (regapp "TSP_LISP_POST"))
                           (entmake (list '(0 . "INSERT") (cons 2 post-block) (cons 8 "_중간말뚝(Post pile)") (cons 62 256) (cons 10 ins_pt) '(41 . 1.0) (cons 42 y_scale) '(43 . 1.0) (cons 50 rot)
                                          (list -3 (list "TSP_LISP_POST" (cons 1000 "MANUAL_POST")))
                                    ))
                           (setq session-ents (cons (entlast) session-ents))
                         )
                       )
                       (princ "\n[완료] 중간말뚝 추가 완료.")
                     )
                     (princ "\n[오류] 클릭한 교차점에 보강재(Brace)가 지나가지 않습니다.")
                   )
                 )
                 (princ "\n[오류] 반경 내에 보강재(Brace) 객체가 없습니다.")
               )
             )
             (princ "\n[오류] 두 선이 만나는 정확한 '교차점'이 아닙니다. 스냅을 이용해 다시 클릭하세요.")
           )
             ) ;; end TRI 경로
           ) ;; end if RECT/TRI 분기
         )
       )
      )
    )
  )
  
  (setvar "OSMODE" old-osmode)
  (princ "\n[종료] 수동 추가 완료.")
  (princ)
)

;;;;==========================================================================
;;;; defun tsp-sanitize-support-list : 지보재 리스트 내 오염 데이터 제거 및 ARX 크래시 방지용 강제 복원
;;;;==========================================================================
(defun tsp-sanitize-support-list (sup-list / clean-list item-type new-item opt)
  (setq clean-list '())
  (if sup-list
    (foreach item sup-list
      (if (and (listp item) (> (length item) 0))
        (progn
          (setq item-type (car item))
          ;; ADD_POST 등 제어 문자열이 포함된 패킷은 제외하고 정상 데이터만 필터링
          (if (and item-type (= (type item-type) 'STR) (not (wcmatch item-type "*_POST")))
            (progn
              (setq new-item item)
              ;; [ARX 크래시 핵심 방어] 버팀보 데이터 중 보강재 옵션(11번째 인덱스)이 과거 버그로 인해 문자열로 오염된 경우 리스트로 강제 복원
              (if (wcmatch item-type "버팀보*")
                (if (> (length item) 11)
                  (progn
                    (setq opt (nth 11 item))
                    (if (= (type opt) 'STR)
                      (progn
                        ;; 문자열 상태의 옵션("(\"1\" \"0\"...)")을 진짜 리스트로 파싱
                        (setq opt (read opt))
                        ;; 안전한 리스트로 파싱된 데이터를 원래 위치에 끼워넣어 정상 레코드로 재조립
                        (setq new-item (list (nth 0 item) (nth 1 item) (nth 2 item) (nth 3 item) (nth 4 item) (nth 5 item) (nth 6 item) (nth 7 item) (nth 8 item) (nth 9 item) (nth 10 item) opt))
                      )
                    )
                  )
                )
              )
              (setq clean-list (append clean-list (list new-item)))
            )
          )
        )
      )
    )
  )
  clean-list
)

;;;;==========================================================================
;;;; defun tsp-manual-delete-post : 다중 영역/드래그 선택 및 연속 삭제
;;;;==========================================================================
(defun tsp-manual-delete-post (active-seg-id / ss i ent ent-data blk-name pt-orig ins-pt p1 p2 ss-dup j dup-ent dup-data del-count loop valid-triangles ss-struts e-data xdata x-vals t-p1 t-p2 t-p3 is-inside tri skipped-count check-id)
  (princ (strcat "\n[안내] Seg-" (itoa active-seg-id) " 수동 삭제 작업을 시작합니다."))
  (setq loop T)
  
  ;; 1. 현재 타겟 세그먼트와 일치하는 모든 사보강재(삼각형) 및 버팀보(사각형) 영역을 수집
  (setq valid-triangles '())
  (setq ss-struts (ssget "X" '((0 . "LWPOLYLINE") (8 . "_사보강재(Corner_Strut),_버팀보(Strut)"))))
  (if ss-struts
    (progn
      (setq j 0)
      (while (< j (sslength ss-struts))
        (setq e-data (entget (ssname ss-struts j) '("TSP_STRUT_SPEC")))
        (setq cur-layer (cdr (assoc 8 e-data)))
        (setq xdata (assoc -3 e-data))
        (if xdata
          (progn
            (setq x-vals (cdr (car (cdr xdata))))
            ;; [버그수정] 사보강재 XDATA 길이=8, 버팀보 XDATA 길이=10 → (>= length 8)로 통합 처리
            (if (>= (length x-vals) 8)
              (progn
                (setq check-id (cdr (nth 0 x-vals)))
                ;; ID가 일치하는 구역만 유효 구역으로 수집
                (if (= check-id active-seg-id)
                  (if (= cur-layer "_사보강재(Corner_Strut)")
                    (progn
                      ;; 사보강재 데이터 수집 (TRI)
                      (setq t-p1 (cdr (nth 5 x-vals)))
                      (setq t-p2 (cdr (nth 6 x-vals)))
                      (setq t-p3 (cdr (nth 7 x-vals)))
                      (setq valid-triangles (append valid-triangles (list (list "TRI" t-p1 t-p2 t-p3))))
                    )
                    (progn
                      ;; 버팀보 데이터 수집 (RECT) - XDATA 길이 10
                      (setq s-p1 (cdr (nth 2 x-vals)))
                      (setq s-p2 (cdr (nth 3 x-vals)))
                      (setq s-width (cdr (nth 1 x-vals)))
                      (setq valid-triangles (append valid-triangles (list (list "RECT" s-p1 s-p2 s-width))))
                    )
                  )
                )
              )
            )
          )
        )
        (setq j (1+ j))
      )
    )
  )

  (while loop
    (princ (strcat "\n[수동 삭제] Seg-" (itoa active-seg-id) " 구역 내의 객체를 선택하세요 (다중 선택/드래그 가능, 종료: Enter/ESC): "))
    (setq ss (vl-catch-all-apply 'ssget (list '((0 . "INSERT") (8 . "_중간말뚝(Post pile)")))))
    
    (cond
      ((vl-catch-all-error-p ss)
       (setq loop nil)
       (princ "\n[취소] 사용자가 ESC를 눌러 삭제 작업을 중단했습니다.")
      )
      ((not ss)
       (setq loop nil)
      )
      ((= (type ss) 'PICKSET)
       (setq i 0 del-count 0 skipped-count 0)
       (while (< i (sslength ss))
         (setq ent (ssname ss i))
         (if (entget ent)
           (progn
             (setq ent-data (entget ent))
             (setq blk-name (cdr (assoc 2 ent-data)))
             
             (if (wcmatch (strcase blk-name) "_POST_PILE*")
               (progn
                 (setq pt-orig (cdr (assoc 10 ent-data)))
                 (setq ins-pt (list (car pt-orig) (cadr pt-orig) 0.0))
                 
                 ;; 선택된 객체가 타겟 세그먼트의 유효 영역 내부에 있는지 확인 (다중 모양 대응)
                 (setq is-inside nil)
                 (foreach tri valid-triangles
                   (if (= (car tri) "TRI")
                     (if (tsp-is-point-in-triangle ins-pt (nth 1 tri) (nth 2 tri) (nth 3 tri)) (setq is-inside T))
                     (progn
                       (setq s-p1 (nth 1 tri) s-p2 (nth 2 tri) s-width (nth 3 tri))
                       (setq s-ang (angle s-p1 s-p2))
                       (setq d-proj (tsp-project-dist s-p1 s-ang ins-pt))
                       (setq d-perp (abs (- (* (- (car ins-pt) (car s-p1)) (sin s-ang)) (* (- (cadr ins-pt) (cadr s-p1)) (cos s-ang)))))
                       (if (and (>= d-proj -10.0) (<= d-proj (+ (distance s-p1 s-p2) 10.0)) (<= d-perp (+ s-width 100.0)))
                         (setq is-inside T)
                       )
                     )
                   )
                 )
                 
                 (if is-inside
                   (progn
                     (if *tsp-use-temp-posts*
                       (setq *tsp-temp-deleted-posts* (append *tsp-temp-deleted-posts* (list ins-pt)))
                       (progn
                         (setq *tsp-deleted-post-points* (vlax-ldata-get "TSP_DICT" "DELETED_POSTS"))
                         (if (not *tsp-deleted-post-points*) (setq *tsp-deleted-post-points* '()))
                         (setq *tsp-deleted-post-points* (append *tsp-deleted-post-points* (list ins-pt)))
                         (vlax-ldata-put "TSP_DICT" "DELETED_POSTS" *tsp-deleted-post-points*)
                       )
                     )
                     
                     (setq p1 (list (- (car ins-pt) 5.0) (- (cadr ins-pt) 5.0)))
                     (setq p2 (list (+ (car ins-pt) 5.0) (+ (cadr ins-pt) 5.0)))
                     (setq ss-dup (ssget "C" p1 p2 '((0 . "INSERT"))))
                     (if ss-dup
                       (progn
                         (setq j 0)
                         (while (< j (sslength ss-dup))
                           (setq dup-ent (ssname ss-dup j))
                           (if (entget dup-ent)
                             (progn
                               (setq dup-data (entget dup-ent))
                               (if (and (= (strcase (cdr (assoc 8 dup-data))) (strcase "_중간말뚝(Post pile)"))
                                        (wcmatch (strcase (cdr (assoc 2 dup-data))) "_POST_PILE*"))
                                 (entdel dup-ent)
                               )
                             )
                           )
                           (setq j (1+ j))
                         )
                       )
                     )
                     
                     (if (entget ent) (entdel ent))
                     (setq del-count (1+ del-count))
                   )
                   (setq skipped-count (1+ skipped-count))
                 )
               )
             )
           )
         )
         (setq i (1+ i))
       )
       
       (setq *tsp-data-dirty* T)
       (command "_.REGEN")
       
       (if (> del-count 0) (princ (strcat "\n[완료] " (itoa del-count) "개의 중간말뚝이 삭제되었습니다.")))
       (if (> skipped-count 0) (princ (strcat "\n[오류 차단] 해당 구역 외부의 객체 " (itoa skipped-count) "개는 보호되어 삭제되지 않았습니다.")))
      )
    )
  )
  (princ "\n[종료] 삭제 완료.")
  (princ)
)


;;;;==========================================================================
;;;; defun tsp-reset-post-manual : 중간말뚝 수동 삭제 및 추가 기록 모두 초기화 및 도면 객체 청소
;;;;==========================================================================
(defun tsp-reset-post-manual ( / ss i )
  ;; 1. 도면에 영구적으로 박제된(Bake) 중간말뚝 블록 객체를 모두 찾아 물리적 삭제
  (setq ss (ssget "X" '((0 . "INSERT") (8 . "_중간말뚝(Post pile)"))))
  (if ss
    (progn
      (setq i 0)
      (while (< i (sslength ss))
        (entdel (ssname ss i))
        (setq i (1+ i))
      )
    )
  )

  ;; 2. 메모리 및 LDATA 기록 완전 삭제
  (if *tsp-use-temp-posts*
    (progn
      (setq *tsp-temp-added-posts* '())
      (setq *tsp-temp-deleted-posts* '())
    )
    (progn
      ;; 빈 리스트를 덮어쓰지 않고 LDATA 딕셔너리에서 항목 자체를 완전히 삭제
      (vlax-ldata-delete "TSP_DICT" "ADDED_POSTS")
      (vlax-ldata-delete "TSP_DICT" "DELETED_POSTS")
    )
  )
  (setq *tsp-data-dirty* T)
  
  ;; 3. 화면 갱신 (기존 말뚝이 모두 지워진 상태에서 자동 배치 설정된 말뚝들만 새로 깔끔하게 그려짐)
  (if (and (boundp '*tsp-boundary-ent*) *tsp-boundary-ent* (boundp '*tsp-boundary-orient*) *tsp-boundary-orient*)
    (progn
      (tsp-redraw-realtime-plan *tsp-boundary-ent* *tsp-boundary-orient*)
      (princ "\n중간말뚝 추가/삭제 기록 초기화 및 객체 청소 완료")
    )
    (princ "\n 중간말뚝 추가/삭제 기록 초기화 및 객체 청소 완료")
  )
  (princ)
)


;;; ==========================================================================
;;; [SECTION 7] 메인 실행 명령어 (Main Commands)
;;; ==========================================================================


;;;;==========================================================================
;;;; defun tsp-zoom-to-right-half : 평면도 전용 화면 우측 정렬 줌
;;;;==========================================================================
(defun tsp-zoom-to-right-half (vertices / minX maxX minY maxY w h newMinX newMaxX newMinY newMaxY)
  (setq minX (apply 'min (mapcar 'car vertices)))
  (setq maxX (apply 'max (mapcar 'car vertices)))
  (setq minY (apply 'min (mapcar 'cadr vertices)))
  (setq maxY (apply 'max (mapcar 'cadr vertices)))
  (setq w (- maxX minX) h (- maxY minY))
  (setq minX (- minX (* w 0.3)) maxX (+ maxX (* w 0.3)))
  (setq minY (- minY (* h 0.3)) maxY (+ maxY (* h 0.3)))
  (setq w (- maxX minX) h (- maxY minY))
  ;; 평면도는 기본 비율(w) 적용
  (setq newMinX (- minX w))
  (setq newMaxX maxX)
  (setq newMinY minY)
  (setq newMaxY maxY)
  (command "_.ZOOM" "_W" (list newMinX newMinY) (list newMaxX newMaxY))
  (princ)
)


;;;;==========================================================================
;;;; defun tsp-zoom-legend : 범례 전용 화면 우측 정렬 줌
;;;;==========================================================================
(defun tsp-zoom-legend (vertices / minX maxX minY maxY w h newMinX newMaxX newMinY newMaxY)
  (setq minX (apply 'min (mapcar 'car vertices)))
  (setq maxX (apply 'max (mapcar 'car vertices)))
  (setq minY (apply 'min (mapcar 'cadr vertices)))
  (setq maxY (apply 'max (mapcar 'cadr vertices)))
  (setq w (- maxX minX) h (- maxY minY))
  (setq minX (- minX (* w 0.3)) maxX (+ maxX (* w 0.3)))
  (setq minY (- minY (* h 0.3)) maxY (+ maxY (* h 0.3)))
  (setq w (- maxX minX) h (- maxY minY))
  ;; 범례는 대화상자를 피하기 위해 1.6배(1.6*w) 적용
  (setq newMinX (- minX (* w 1.6)))
  (setq newMaxX maxX)
  (setq newMinY minY)
  (setq newMaxY maxY)
  (command "_.ZOOM" "_W" (list newMinX newMinY) (list newMaxX newMaxY))
  (princ)
)
;;; ==========================================================================
;;; 실시간 중첩 방지 작도 (Real-time Redraw with Clean-up)
;;; ==========================================================================
(if (not (boundp '*tsp-realtime-entities*)) (setq *tsp-realtime-entities* '()))


;;;;==========================================================================
;;;; defun tsp-redraw-realtime-plan : 실시간 작도 시 도면(DWG)에 영구 저장된 중간말뚝 삭제 기록 필터링 유지
;;;;==========================================================================
(defun tsp-redraw-realtime-plan (boundary-ent boundary-orient / next-ent ent-data blk-name layer-name pt is-deleted post-data
                                  orphan-ent xdata-strut xdata-post xdata-brace xdata cur-boundary-handle)
  (if (and (boundp '*tsp-data-dirty*) (not *tsp-data-dirty*))
    (princ "\n 변경된 내용이 없어 재작도를 생략합니다.")
    (progn
      ;; 설정창(다이얼로그) 세션 중에는 임시 데이터를 사용, 평상시엔 LDATA 영구 기록 사용
      (if *tsp-use-temp-posts*
        (progn
          (setq *tsp-deleted-post-points* *tsp-temp-deleted-posts*)
          (setq *tsp-added-post-points* *tsp-temp-added-posts*)
        )
        (progn
          (setq *tsp-deleted-post-points* (vlax-ldata-get "TSP_DICT" "DELETED_POSTS"))
          (if (not *tsp-deleted-post-points*) (setq *tsp-deleted-post-points* '()))
          (setq *tsp-added-post-points* (vlax-ldata-get "TSP_DICT" "ADDED_POSTS"))
          (if (not *tsp-added-post-points*) (setq *tsp-added-post-points* '()))
        )
      )
      ;; 1. ARX가 관리하는 객체(TSP_GRP_241 등)는 ARX가 자체 정리하므로 LISP 단에서 물리적 삭제(entdel)를 금지함!
      ;; *tsp-realtime-entities* 리스트는 연속 보강재 참조용으로만 리셋
      (setq *tsp-realtime-entities* '())
      
      ;; 현재 작업 중인 경계선(boundary-ent) 핸들을 추출
      (setq cur-boundary-handle (cdr (assoc 5 (entget boundary-ent)))) 
      (setq orphan-ent (entnext))
      (while orphan-ent
        ;; 삭제(entdel)된 객체에 entnext를 호출하면 nil이 반환되어 루프가 즉시 끊깁니다.
        ;; 따라서 현재 객체를 검사/삭제하기 전에 무조건 '다음 객체'를 미리 안전하게 확보해 두어야 합니다.
        (setq next-orphan (vl-catch-all-apply 'entnext (list orphan-ent)))
        (if (vl-catch-all-error-p next-orphan) (setq next-orphan nil))
        
        (setq is-deleted nil) ;; 하나의 객체에 대해 중복 삭제 시도를 방지하는 플래그

        ;; 세 APPID 각각 독립적으로 조회
        (setq xdata-strut (assoc -3 (vl-catch-all-apply 'entget (list orphan-ent '("TSP_STRUT_SPEC")))))
        (setq xdata-post  (assoc -3 (vl-catch-all-apply 'entget (list orphan-ent '("TSP_LISP_POST")))))
        (setq xdata-brace (assoc -3 (vl-catch-all-apply 'entget (list orphan-ent '("TSP_LISP_BRACE")))))

        ;; TSP_STRUT_SPEC: 레거시 CONT_BRACE 제거
        (if (and (not is-deleted) xdata-strut (listp xdata-strut))
          (progn
            (setq xdata (vl-catch-all-apply 'cdadr (list xdata-strut)))
            (if (and xdata (not (vl-catch-all-error-p xdata)) (listp xdata)
                     (> (length xdata) 8))
              (progn
                (setq tag-name (cdr (nth 7 xdata)))
                (setq saved-handle (cdr (nth 8 xdata)))
                ;; 도면에서 이미 지워진 '유령 경계선'인지 판별
                (setq is-ghost (if (and saved-handle (= (type saved-handle) 'STR)) (not (and (handent saved-handle) (entget (handent saved-handle)))) T))
                (if (and (= tag-name "CONT_BRACE")
                         (or (= saved-handle cur-boundary-handle) is-ghost))
                  (progn
                    (setq is-deleted T)
                  )
                )
              )
            )
          )
        )

        ;; TSP_LISP_POST: MANUAL_POST 제거
        (if (and (not is-deleted) xdata-post (listp xdata-post))
          (progn
            (setq xdata (vl-catch-all-apply 'cdadr (list xdata-post)))
            (if (and xdata (not (vl-catch-all-error-p xdata)) (listp xdata)
                     (> (length xdata) 0)
                     (= (cdr (nth 0 xdata)) "MANUAL_POST"))
              (progn
                (setq is-deleted T)
              )
            )
          )
        )

        ;; TSP_LISP_BRACE: CONT_BRACE 및 MID_GAP 제거
        (if (and (not is-deleted) xdata-brace (listp xdata-brace))
          (progn
            (setq xdata (vl-catch-all-apply 'cdadr (list xdata-brace)))
            (if (and xdata (not (vl-catch-all-error-p xdata)) (listp xdata)
                     (> (length xdata) 8))
              (progn
                (setq tag-name (cdr (nth 7 xdata)))
                (setq saved-handle (cdr (nth 8 xdata)))
                (setq is-ghost (if (and saved-handle (= (type saved-handle) 'STR)) (not (and (handent saved-handle) (entget (handent saved-handle)))) T))
                (if (and (or (= tag-name "CONT_BRACE") (= tag-name "MID_GAP"))
                         (or (= saved-handle cur-boundary-handle) is-ghost))
                  (progn
                    (setq is-deleted T)
                  )
                )
              )
            )
          )
        )

        ;; 미리 확보해둔 다음 객체로 넘어가기
        (setq orphan-ent next-orphan)
      )

      ;; 2. 도면 새로 그리기 시작 지점 마킹
      (setq next-ent (entlast))
      (setq group-start-ent next-ent)
      (if next-ent
        (tsp-log "[Redraw] 작도 시작 전 (entlast) 기준점 확보 성공.")
        (tsp-log "[Redraw] 경고! 작도 시작 전 (entlast)가 nil입니다.")
      )
      
      ;; ==========================================================================
      ;; 3. 실제 작도 함수 호출
      ;; ==========================================================================
      ;; 데이터 무결성을 위해 원본 세그먼트 리스트 백업
      (setq original-segment-list *segment-list*)
      (setq temp-segment-list '())
      
      ;; 전체 데이터를 스캔하여 배열 버팀보의 보강재 옵션만 임시로 "0"(꺼짐)으로 변조
      (foreach seg *segment-list*
        (setq supp-list (tsp-sanitize-support-list (cdr (assoc 'SUPPORT-LIST seg))))
        (setq new-supp-list '())
        (if supp-list
          (foreach supp supp-list
            (if (wcmatch (car supp) "버팀보*")
              (progn
                (setq opt (if (> (length supp) 11) (nth 11 supp) nil))
                (if (and opt (= (nth 0 opt) "1"))
                  (progn
                    ;; 11번째 인덱스의 첫 번째 값("1")을 "0"으로 변경하여 하위 함수의 개별 작도 무력화
                    (setq new-opt (cons "0" (cdr opt)))
                    (setq i 0 new-supp '())
                    (foreach item supp
                      (if (= i 11)
                        (setq new-supp (cons new-opt new-supp))
                        (setq new-supp (cons item new-supp))
                      )
                      (setq i (1+ i))
                    )
                    (setq new-supp-list (cons (reverse new-supp) new-supp-list))
                  )
                  (setq new-supp-list (cons supp new-supp-list))
                )
              )
              (setq new-supp-list (cons supp new-supp-list))
            )
          )
        )
        (setq temp-segment-list (cons (subst (cons 'SUPPORT-LIST (reverse new-supp-list)) (assoc 'SUPPORT-LIST seg) seg) temp-segment-list))
      )
      
      ;; 임시 변조된 리스트를 전역 변수에 덮어씌워 일괄 작도 실행
      (setq *segment-list* (reverse temp-segment-list))
      ;; 핵심 ARX 작도 함수 호출
      (vl-catch-all-apply 'create-hpile-set-on-boundary (list boundary-ent boundary-orient))
      ;; 작도가 끝나면 즉시 원본 리스트 복구
      (setq *segment-list* original-segment-list)

      ;; 3-1. 수동으로 추가된 중간말뚝 작도
      (if *tsp-added-post-points*
        (progn
          ;; ARX 크래시 방지 전용 APPID 사용
          (if (not (tblsearch "APPID" "TSP_LISP_POST")) (regapp "TSP_LISP_POST"))
          (foreach post-data *tsp-added-post-points*
            (setq y_scale (if (> (length post-data) 2) (nth 2 post-data) 1.0))
            (setq custom-h  (if (> (length post-data) 3) (nth 3 post-data) 300.0))
            (setq custom-b  (if (> (length post-data) 4) (nth 4 post-data) 300.0))
            (setq custom-tw (if (> (length post-data) 5) (nth 5 post-data) 10.0))
            (setq custom-tf (if (> (length post-data) 6) (nth 6 post-data) 15.0))
            
            (entmake (list '(0 . "INSERT") 
                           (cons 2 (create-post-pile-block custom-h custom-b custom-tw custom-tf)) 
                           (cons 8 "_중간말뚝(Post pile)") 
                           (cons 62 256) 
                           (cons 10 (car post-data)) 
                           '(41 . 1.0) (cons 42 y_scale) '(43 . 1.0) 
                           (cons 50 (cadr post-data))
                           (list -3 (list "TSP_LISP_POST" (cons 1000 "MANUAL_POST")))
                     ))
          )
        )
      )
      
      ;; 4. 방금 새로 생성된 객체를 추적 리스트에 담으면서 삭제된 말뚝 필터링
      (while (setq next-ent (entnext next-ent))
        (setq *tsp-realtime-entities* (cons next-ent *tsp-realtime-entities*))
        
        ;; [수동 삭제 영구 필터링 로직] 블랙리스트 좌표에 속한 객체는 화면에 보이기 전 강제 제거
        (if (and *tsp-deleted-post-points* (> (length *tsp-deleted-post-points*) 0))
          (progn
            (setq ent-data (entget next-ent))
            (if (= (cdr (assoc 0 ent-data)) "INSERT")
              (progn
                (setq layer-name (cdr (assoc 8 ent-data)))
                (setq blk-name (cdr (assoc 2 ent-data)))
                (if (and layer-name blk-name
                         (= (strcase layer-name) (strcase "_중간말뚝(Post pile)")) 
                         (wcmatch (strcase blk-name) "_POST_PILE*"))
                  (progn
                    (setq pt (cdr (assoc 10 ent-data)))
                    (setq pt (list (car pt) (cadr pt) 0.0))
                    (setq is-deleted nil)
                    (foreach del-pt *tsp-deleted-post-points*
                      (if (< (distance pt del-pt) 10.0)
                        (setq is-deleted T)
                      )
                    )
                    ;; [ARX 붕괴 완벽 차단] entdel 대신 객체 투명화(DXF 60) 부여
                    ;; 객체가 메모리에 살아있으므로 ARX 그룹 정리 시 튕기는 현상 원천 차단
                    (if is-deleted
                      (progn
                        (setq edata (entget next-ent))
                        (if (not (assoc 60 edata))
                          (entmod (append edata (list (cons 60 1))))
                          (entmod (subst (cons 60 1) (assoc 60 edata) edata))
                        )
                      )
                    )
                  )
                )
              )
            )
          )
        )
      )
      ;; [Phase 1] 루프 후 원위치 정렬 (삭제 객체 제외)
      (setq *tsp-realtime-entities* (reverse *tsp-realtime-entities*))
      (princ (strcat "\n[디버그: TSP] 루프 종료 후 최종 추적된 신규 객체 수: " (itoa (length *tsp-realtime-entities*))))
      
      ;; ==========================================================================
      ;; 5. 엑셀 불러오기 및 일괄 작도 시 연속 보강재 완벽 복원 로직 (XDATA 연동)
      ;; ==========================================================================
      (if (and (boundp '*segment-list*) *segment-list*)
        (foreach seg *segment-list*
          (setq support-list (cdr (assoc 'SUPPORT-LIST seg)))
          (if support-list
            (foreach support support-list
              (if (wcmatch (car support) "버팀보*")
                (progn
                  (setq s-brace-opt (if (> (length support) 11) (nth 11 support) nil))
                  (if (and s-brace-opt (= (nth 0 s-brace-opt) "1"))
                    (progn
                      (setq manual-pts (if (> (length support) 8) (nth 8 support) '()))
                      (if (and manual-pts (> (length manual-pts) 0))
                        (progn
                          (setq sec-str (if (> (length support) 6) (nth 6 support) ""))
                          (setq count-val (if (> (length support) 4) (nth 4 support) 1))
                          (setq is-double (if (>= count-val 2) T nil))
                          
                          ;; 3D 좌표 충돌(에러) 방지 및 진짜 pt1 추출 리스트
                          (setq strut-ang nil strut-len nil real-pts-list '())
                          
                          ;; manual-pts의 각 점마다 실제 도면에 그려진 버팀보의 진짜 pt1(안쪽 면)을 역추적
                          (foreach pt-raw manual-pts
                            (setq pt-base (list (car pt-raw) (cadr pt-raw) 0.0))
                            (setq matched-pt1 nil)
                            
                            (foreach ent *tsp-realtime-entities*
                              (if (not matched-pt1)
                                (progn
                                  (setq edata (if (entget ent) (entget ent '("TSP_STRUT_SPEC")) nil))
                                  (if (and edata (assoc -3 edata))
                                    (progn
                                      (setq xvals (cdr (car (cdr (assoc -3 edata)))))
                                      (if (and (> (length xvals) 7) (= (cdr (nth 7 xvals)) "MANUAL_STRUT"))
                                        (progn
                                          (setq pt1-raw (cdr (nth 2 xvals)) pt2-raw (cdr (nth 3 xvals)))
                                          (if (and pt1-raw pt2-raw)
                                            (progn
                                              (setq x-pt1 (list (car pt1-raw) (cadr pt1-raw) 0.0))
                                              (setq x-pt2 (list (car pt2-raw) (cadr pt2-raw) 0.0))
                                              (setq line-ang (angle x-pt1 x-pt2))
                                              
                                              ;; 수직 거리 매칭 (단차 무시, 동일 축 확인)
                                              (setq dist-to-line (abs (tsp-project-dist x-pt1 (+ line-ang (/ pi 2.0)) pt-base)))
                                              ;; 수평 거리 매칭 (동일 선상의 다른 버팀보와 구분, 오차 넉넉히 허용)
                                              (setq dist-along (tsp-project-dist x-pt1 line-ang pt-base))
                                              
                                              (if (and (< dist-to-line 10.0) (>= dist-along -1000.0) (<= dist-along (+ (distance x-pt1 x-pt2) 1000.0)))
                                                (progn
                                                  (setq matched-pt1 x-pt1) ;; 진짜 pt1 획득 성공!
                                                  (if (not strut-ang)
                                                    (progn
                                                      (setq strut-ang line-ang)
                                                      (setq strut-len (distance x-pt1 x-pt2))
                                                    )
                                                  )
                                                )
                                              )
                                            )
                                          )
                                        )
                                      )
                                    )
                                  )
                                )
                              )
                            )
                            (if matched-pt1 (setq real-pts-list (cons matched-pt1 real-pts-list)))
                          )
                          
                          (setq real-pts-list (reverse real-pts-list))
                          
                          ;; 진짜 pt1 좌표 리스트를 기반으로 연속 보강재 작도 실행
                          (if (and strut-ang strut-len (> (length real-pts-list) 0))
                            (progn
                              ;; 상위 루프에서 순회 중인 현재 세그먼트(seg)의 ID를 추출하여 전달
                              (setq current-seg-id (cdr (assoc 'ID seg)))
                              (setq batch-braces (vl-catch-all-apply 'tsp-draw-realtime-continuous-braces (list real-pts-list s-brace-opt sec-str is-double strut-ang strut-len current-seg-id)))
                              (if (and batch-braces (not (vl-catch-all-error-p batch-braces)))
                                ;; batch-braces 자체가 리스트이므로 append 사용
                                (setq *tsp-realtime-entities* (append *tsp-realtime-entities* batch-braces))
                              )
                            )
                          )
                        )
                      )
                    )
                  )
                )
              )
            )
          )
        )
      )
      ;; ==========================================================================
      ;; 6. 연속 보강재(TSP_LISP_BRACE) 객체를 TSP_GRP 그룹에 포함하여 재그룹화
      ;; ==========================================================================
      (tsp-group-last-entities group-start-ent boundary-ent) ;; [버그 해결] 소진된 next-ent 대신 보존해둔 group-start-ent 사용
      
      ;; [화면 갱신 누락 픽스]
      (vl-catch-all-apply 'vla-regen (list (vla-get-activedocument (vlax-get-acad-object)) 1))

      ;; [자동저장 완벽 분리] 실제 작도가 일어났으므로 자동저장 전용 플래그를 T로 마킹
      (setq *tsp-project-modified* T)
      
      (setq *tsp-data-dirty* nil)
    )
  )
)

;;;;==========================================================================
;;;; defun tsp-fix-mirrored-polyline : 경계선 Z축 양수화(OCS 좌표계 재조정)
;;;;==========================================================================
(defun tsp-fix-mirrored-polyline (ent / ent-data normal new-data item pt bulge)
  (setq ent-data (entget ent))
  (setq normal (cdr (assoc 210 ent-data)))
  (if (and normal (< (caddr normal) 0.0))
    (progn
      (princ "\n[시스템] OCS 좌표 및 Z축을 양수(+)로 자동 보정")
      (setq new-data '())
      (foreach item ent-data
        (cond
          ((= (car item) 10)
           (setq pt (cdr item))
           (setq new-data (append new-data (list (cons 10 (list (- (car pt)) (cadr pt))))))
          )
          ;; 곡선(Bulge) 부호 반전
          ((= (car item) 42)
           (setq bulge (cdr item))
           (setq new-data (append new-data (list (cons 42 (- bulge)))))
          )
          ;; Extrusion Direction (Z축) 정상화
          ((= (car item) 210)
           (setq new-data (append new-data (list (cons 210 '(0.0 0.0 1.0)))))
          )
          (t
           (setq new-data (append new-data (list item)))
          )
        )
      )
      ;; 객체 업데이트
      (entmod new-data)
      (entupd ent)
      T
    )
    nil
  )
)


;;; ==========================================================================
;;; [section 8] EXCEL(CSV) Export / Import 관련 모듈
;;; ==========================================================================

;;;;==========================================================================
;;;; defun tsp-split-string-by-comma : 문자열을 쉼표 단위로 분할하여 리스트 반환
;;;;==========================================================================
(defun tsp-split-string-by-comma (str / pos lst)
  (setq lst nil)
  (while (setq pos (vl-string-search "," str))
    (setq lst (append lst (list (substr str 1 pos))))
    (setq str (substr str (+ pos 2)))
  )
  (append lst (list str))
)

;;;;==========================================================================
;;;; defun tsp-select-project-for-export : 내보낼 프로젝트를 DCL에서 선택
;;;;==========================================================================
(defun tsp-select-project-for-export (/ dict proj-list dcl-id dcl-path dcl-file selected-proj idx)
  (setq dict (dictsearch (namedobjdict) "TSP_DATA_DICT"))
  (if (not dict)
    (progn (alert "도면에 저장된 프로젝트 데이터가 없습니다.") nil)
    (progn
      (setq proj-list nil)
      (foreach item dict
        (if (= (car item) 3)
          (setq proj-list (append proj-list (list (cdr item))))
        )
      )
      (if (= (length proj-list) 0)
        (progn (alert "저장된 프로젝트가 없습니다.") nil)
        (progn
          (setq dcl-path (strcat (getvar "TEMPPREFIX") "tsp_export.dcl"))
          (setq dcl-file (open dcl-path "w"))
          (write-line "tsp_export_dlg : dialog { label = \"내보낼 프로젝트 선택\";" dcl-file)
          (write-line "  : list_box { key = \"proj_list\"; height = 10; width = 40; }" dcl-file)
          (write-line "  : row { : button { key = \"accept\"; label = \"확인(Export)\"; is_default = true; } : button { key = \"cancel\"; label = \"취소\"; is_cancel = true; } }" dcl-file)
          (write-line "}" dcl-file)
          (close dcl-file)

          (setq dcl-id (load_dialog dcl-path))
          (if (new_dialog "tsp_export_dlg" dcl-id)
            (progn
              (start_list "proj_list")
              (mapcar 'add_list proj-list)
              (end_list)
              (setq selected-proj nil)
              (action_tile "proj_list" "(setq idx (atoi $value))")
              (action_tile "accept" "(if idx (setq selected-proj (nth idx proj-list))) (done_dialog 1)")
              (action_tile "cancel" "(done_dialog 0)")
              (start_dialog)
              (unload_dialog dcl-id)
              selected-proj
            )
            (progn (alert "DCL 로드 실패") nil)
          )
        )
      )
    )
  )
)


;;;;==========================================================================
;;;; defun tsp-export-to-csv : 선택된 프로젝트를 CSV 파일로 출력
;;;;==========================================================================
(defun tsp-export-to-csv (/ proj-name file-path file-desc seg-str data-pack)
  (setq proj-name (tsp-select-project-for-export))
  (if proj-name
    (progn
      ;; 도면 검증 로직이 포함된 tsp-load-project-data 대신, 딕셔너리에서 원본 데이터를 직접 추출 (Bypass)
      (setq data-pack (vlax-ldata-get "TSP_DATA_DICT" proj-name))
      (if (not data-pack)
        (alert "프로젝트 데이터를 읽을 수 없습니다.")
        (progn
          ;; 내보내기에 필요한 데이터만 전역 변수 메모리로 세팅
          (setq *segment-list* (nth 0 data-pack))
          (setq *tsp-current-project-name* proj-name)
          (setq *tsp-scale-section* (nth 13 data-pack))
          (setq *tsp-scale-plan* (nth 14 data-pack))
          (setq *tsp-soil-layers* (nth 9 data-pack))

          (setq file-path (getfiled "EXCEL(CSV)로 내보내기" (strcat proj-name ".csv") "csv" 1))
          (if file-path
            (progn
              (setq file-desc (open file-path "w"))
              
              ;; 글로벌 데이터 기록
              (write-line (strcat "#GLOBAL,PROJECT_NAME," *tsp-current-project-name* ",SCALE_S," (itoa *tsp-scale-section*) ",SCALE_P," (itoa *tsp-scale-plan*)) file-desc)
              
              ;; 프로젝트 전역 설정(Global Settings) 100% 백업용 RAW 데이터 기록
              (write-line (strcat "#GLOBAL_RAW," (vl-prin1-to-string data-pack)) file-desc)
              
              ;; 지반 지층 정보 기록
              (foreach soil *tsp-soil-layers*
                (write-line (strcat "#SOIL," (vl-prin1-to-string soil)) file-desc)
              )
              
              ;; 세그먼트 데이터 기록 (13번째 열에 원본 리스트 통째로 직렬화하여 백업)
              (write-line "#HEADER,ID,TYPE,V-START,V-END,ANGLE,LENGTH,WALL-SPEC,CTC,MAX-DEPTH,SUPPORT-LIST,CORNER-BRACE,RAW-DATA" file-desc)
              (foreach seg *segment-list*
                (setq seg-str (strcat "SEGMENT,"
                  (if (cdr (assoc 'ID seg)) (itoa (cdr (assoc 'ID seg))) "0") ","
                  
                  ;; 1. 최신 이름표(WALL-TYPE)가 있는지 먼저 확인
                  (cond
                    ((and (cdr (assoc 'WALL-TYPE seg)) (/= (cdr (assoc 'WALL-TYPE seg)) "")) (cdr (assoc 'WALL-TYPE seg)))
                    ((= (cdr (assoc 'HPILE-OR-CIP seg)) 0) "HPILE")
                    ((= (cdr (assoc 'HPILE-OR-CIP seg)) 1) "CIP")
                    (t "HPILE")
                  ) ","
                  
                  ;; 좌표(V-START, V-END) 및 형태(ANGLE, LENGTH)의 정밀도를 소수점 12자리로 극대화
                  (if (cdr (assoc 'V-START seg)) 
                    (strcat "(" (rtos (car (cdr (assoc 'V-START seg))) 2 12) " " (rtos (cadr (cdr (assoc 'V-START seg))) 2 12) " " (rtos (if (caddr (cdr (assoc 'V-START seg))) (caddr (cdr (assoc 'V-START seg))) 0.0) 2 12) ")") 
                    "nil"
                  ) ","
                  (if (cdr (assoc 'V-END seg)) 
                    (strcat "(" (rtos (car (cdr (assoc 'V-END seg))) 2 12) " " (rtos (cadr (cdr (assoc 'V-END seg))) 2 12) " " (rtos (if (caddr (cdr (assoc 'V-END seg))) (caddr (cdr (assoc 'V-END seg))) 0.0) 2 12) ")") 
                    "nil"
                  ) ","
                  (if (cdr (assoc 'ANGLE seg)) (rtos (cdr (assoc 'ANGLE seg)) 2 12) "0.000000000000") ","
                  (if (cdr (assoc 'LENGTH seg)) (rtos (cdr (assoc 'LENGTH seg)) 2 12) "0.000000000000") ","
                  
                  ;; 의도적으로 비워둔 구간에서 WALL-SPEC 등이 nil일 때 strcat이 터지는 것을 방지하는 안전장치 추가
                  (if (cdr (assoc 'WALL-SPEC seg)) (cdr (assoc 'WALL-SPEC seg)) "") ","
                  (if (cdr (assoc 'CTC seg)) (rtos (cdr (assoc 'CTC seg)) 2 3) "") ","
                  (if (cdr (assoc 'MAX-DEPTH seg)) (rtos (cdr (assoc 'MAX-DEPTH seg)) 2 3) "") ","
                  
                  (vl-prin1-to-string (cdr (assoc 'SUPPORT-LIST seg))) ","
                  (vl-prin1-to-string (cdr (assoc 'CORNER-BRACE seg))) ","
                  (vl-prin1-to-string seg)
                ))
                (write-line seg-str file-desc)
              )
              (close file-desc)
              (alert (strcat "[" proj-name "] 데이터가 성공적으로 내보내기 되었습니다.\n파일을 확인해 주세요."))
            )
          )
        )
      )
    )
  )
  (princ)
)


;;;;==========================================================================
;;;; defun tsp-rebuild-boundary : V-START 데이터로 폴리라인 자동 생성
;;;;==========================================================================
(defun tsp-rebuild-boundary (/ pt-list ent)
  (setq pt-list nil)
  (foreach seg *segment-list*
    (setq pt-list (append pt-list (list (cdr (assoc 'V-START seg)))))
  )
  (entmake
    (append
      (list '(0 . "LWPOLYLINE") '(100 . "AcDbEntity") '(100 . "AcDbPolyline")
            (cons 90 (length pt-list))
            '(70 . 1) ; 닫힌 폴리라인 설정
      )
      (mapcar '(lambda (pt) (cons 10 pt)) pt-list)
    )
  )
  (setq ent (entlast))
  (vla-put-Color (vlax-ename->vla-object ent) 1) ; 시인성을 위해 빨간색 지정
  ent
)

;;;;==========================================================================
;;;; defun tsp-import-from-csv : CSV 데이터를 읽어 도면 및 딕셔너리에 복원
;;;;==========================================================================
(defun tsp-import-from-csv (/ file-path file-desc line-str data-lst new-seg-list seg-data new-boundary new-orient ins-opt ins-pt base-pt delta-x delta-y shifted-seg-list old-start old-end new-start new-end raw-globals name-opt new-name pt new-pt rec)
  (setq file-path (getfiled "EXCEL(CSV)에서 불러오기" "" "csv" 0))
  (if file-path
    (progn
      (setq file-desc (open file-path "r"))
      (setq new-seg-list nil)
      (setq *tsp-soil-layers* nil)
      
      (while (setq line-str (read-line file-desc))
        (setq data-lst (tsp-split-string-by-comma line-str))
        (cond
          ((= (nth 0 data-lst) "#GLOBAL")
           (setq *tsp-current-project-name* (nth 2 data-lst))
           (setq *tsp-scale-section* (atoi (nth 4 data-lst)))
           (setq *tsp-scale-plan* (atoi (nth 6 data-lst)))
          )
          ;; 딕셔너리에 들어있던 글로벌 전역 설정 100% 복원
          ((= (nth 0 data-lst) "#GLOBAL_RAW")
           (setq raw-globals (read (nth 1 data-lst)))
           (if raw-globals
             (progn
               (setq *tsp-hpile-spec* (nth 1 raw-globals))
               (setq *tsp-hpile-custom* (nth 2 raw-globals))
               (setq *tsp-wale-spec* (nth 3 raw-globals))
               (setq *tsp-wale-custom* (nth 4 raw-globals))
               (setq *tsp-ctc* (nth 5 raw-globals))
               (setq *tsp-timber-thickness* (nth 6 raw-globals))
               (setq *tsp-max-excavation-depth* (nth 7 raw-globals))
               (setq *tsp-embedment-depth* (nth 8 raw-globals))
               ;; (nth 9)는 #SOIL에서 별도 처리하므로 생략
               (setq *tsp-water-chk* (nth 10 raw-globals))
               (setq *tsp-water-depth* (nth 11 raw-globals))
               (setq *tsp-support-list* (tsp-sanitize-support-list (nth 12 raw-globals)))
               ;; 구버전 프로젝트 호환성 방어 로직
               (if (> (length raw-globals) 15)
                 (progn
                   (setq *tsp-deleted-post-points* (nth 15 raw-globals))
                   (setq *tsp-added-post-points* (nth 16 raw-globals))
                   (vlax-ldata-put "TSP_DICT" "DELETED_POSTS" *tsp-deleted-post-points*)
                   (vlax-ldata-put "TSP_DICT" "ADDED_POSTS" *tsp-added-post-points*)
                 )
                 (progn
                   (setq *tsp-deleted-post-points* '())
                   (setq *tsp-added-post-points* '())
                   (if (vlax-ldata-get "TSP_DICT" "DELETED_POSTS") (vlax-ldata-delete "TSP_DICT" "DELETED_POSTS"))
                   (if (vlax-ldata-get "TSP_DICT" "ADDED_POSTS") (vlax-ldata-delete "TSP_DICT" "ADDED_POSTS"))
                 )
               )
             )
           )
          )
          ((= (nth 0 data-lst) "#SOIL")
           (setq *tsp-soil-layers* (append *tsp-soil-layers* (list (read (nth 1 data-lst)))))
          )
          ((= (nth 0 data-lst) "SEGMENT")
           ;; 1. 13번째 열(RAW-DATA)을 먼저 읽어 뼈대(CIP 및 지반 데이터 등)를 100% 복원
           (setq seg-data (read (nth 12 data-lst)))
           
           ;; 2. 엑셀에서 수정되었을 수 있는 나머지 공통 열의 값으로 데이터 덮어쓰기
           (setq seg-data (subst (cons 'ID (atoi (nth 1 data-lst))) (assoc 'ID seg-data) seg-data))
           (setq seg-data (subst (cons 'NAME (strcat "Seg-" (nth 1 data-lst))) (assoc 'NAME seg-data) seg-data))
           
           ;; 구버전 변수(HPILE-OR-CIP)를 최신 구조인 WALL-TYPE 문자열로 덮어쓰기. 
           ;; 구버전 파일이라 WALL-TYPE 이름표 자체가 없다면 리스트 맨 뒤에 안전하게 추가(append)
           (if (assoc 'WALL-TYPE seg-data)
             (setq seg-data (subst (cons 'WALL-TYPE (nth 2 data-lst)) (assoc 'WALL-TYPE seg-data) seg-data))
             (setq seg-data (append seg-data (list (cons 'WALL-TYPE (nth 2 data-lst)))))
           )
           
           (setq seg-data (subst (cons 'V-START (read (nth 3 data-lst))) (assoc 'V-START seg-data) seg-data))
           (setq seg-data (subst (cons 'V-END (read (nth 4 data-lst))) (assoc 'V-END seg-data) seg-data))
           (setq seg-data (subst (cons 'ANGLE (atof (nth 5 data-lst))) (assoc 'ANGLE seg-data) seg-data))
           (setq seg-data (subst (cons 'LENGTH (atof (nth 6 data-lst))) (assoc 'LENGTH seg-data) seg-data))
           
           ;; 빈칸("")으로 내보낸 데이터를 읽을 때 0이나 0.0이 아닌 원래의 nil 상태로 안전하게 복원
           (setq seg-data (subst (cons 'WALL-SPEC (if (= (nth 7 data-lst) "") nil (nth 7 data-lst))) (assoc 'WALL-SPEC seg-data) seg-data))
           (setq seg-data (subst (cons 'CTC (if (= (nth 8 data-lst) "") nil (atof (nth 8 data-lst)))) (assoc 'CTC seg-data) seg-data))
           (setq seg-data (subst (cons 'MAX-DEPTH (if (= (nth 9 data-lst) "") nil (atof (nth 9 data-lst)))) (assoc 'MAX-DEPTH seg-data) seg-data))
           
           (setq clean-support (tsp-sanitize-support-list (read (nth 10 data-lst))))
           (setq seg-data (subst (cons 'SUPPORT-LIST clean-support) (assoc 'SUPPORT-LIST seg-data) seg-data))
           (setq seg-data (subst (cons 'CORNER-BRACE (read (nth 11 data-lst))) (assoc 'CORNER-BRACE seg-data) seg-data))

           (setq new-seg-list (append new-seg-list (list seg-data)))
          )
        )
      )
      (close file-desc)
      
      (setq *tsp-realtime-entities* nil)
      
      ;; 프로젝트명 중복 시 덮어쓰기 또는 새 이름 지정
      (if (vlax-ldata-get "TSP_DATA_DICT" *tsp-current-project-name*)
        (progn
          (initget "Overwrite New")
          (setq name-opt (getkword (strcat "\n프로젝트 [" *tsp-current-project-name* "] 가 이미 도면 내에 존재합니다. 덮어쓰시겠습니까? [덮어쓰기(O)/새이름(N)] <N>: ")))
          (if (or (not name-opt) (= name-opt "New"))
            (progn
              (setq new-name (getstring T "\n새로운 프로젝트 이름을 입력하세요 (빈칸 입력시 자동생성): "))
              (if (or (not new-name) (= new-name ""))
                (setq *tsp-current-project-name* (tsp-generate-default-project-name))
                (setq *tsp-current-project-name* new-name)
              )
            )
          )
        )
      )
      
      (initget "Origin New")
      (setq ins-opt (getkword "\n불러올 도면의 삽입 방식을 선택하세요 [원래위치(O)/새위치(N)] <N>: "))
      (if (not ins-opt) (setq ins-opt "New"))
      
      (if (= ins-opt "New")
        (progn
          (setq ins-pt (getpoint "\n1번 세그먼트의 시작점이 될 위치를 클릭하세요: "))
          (if ins-pt
            (progn
              (setq ins-pt (trans ins-pt 1 0)) ; WCS 변환
              ;; 첫 번째 세그먼트의 V-START와 클릭한 점 사이의 변위 벡터(거리 및 방향) 계산
              (setq base-pt (cdr (assoc 'V-START (nth 0 new-seg-list))))
              (setq delta-x (- (car ins-pt) (car base-pt)))
              (setq delta-y (- (cadr ins-pt) (cadr base-pt)))
              
              ;; 모든 세그먼트의 V-START, V-END 및 버팀보 수동 좌표(manual-pts)에 변위 벡터를 일괄 적용
                    (setq shifted-seg-list nil)
                    (foreach seg new-seg-list
                      (setq old-start (cdr (assoc 'V-START seg)))
                      (setq old-end (cdr (assoc 'V-END seg)))
                      (setq new-start (list (+ (car old-start) delta-x) (+ (cadr old-start) delta-y) (caddr old-start)))
                      (setq new-end (list (+ (car old-end) delta-x) (+ (cadr old-end) delta-y) (caddr old-end)))
                      (setq seg (subst (cons 'V-START new-start) (assoc 'V-START seg) seg))
                      (setq seg (subst (cons 'V-END new-end) (assoc 'V-END seg) seg))
                      
                      ;; [추가] SUPPORT-LIST 내의 버팀보 수동 배치 절대좌표(manual-pts) 변위 보정
                      (setq old-support (cdr (assoc 'SUPPORT-LIST seg)))
                      (if old-support
                        (progn
                          (setq new-support nil)
                          (foreach s-item old-support
                            (if (wcmatch (car s-item) "버팀보*")
                              (progn
                                (setq s-manual-pts (if (> (length s-item) 8) (nth 8 s-item) nil))
                                (if s-manual-pts
                                  (progn
                                    (setq new-manual-pts (mapcar '(lambda (pt) (list (+ (car pt) delta-x) (+ (cadr pt) delta-y) (caddr pt))) s-manual-pts))
                                    (setq new-s-item '())
                                    (setq idx 0)
                                    (foreach val s-item
                                      (if (= idx 8)
                                        (setq new-s-item (append new-s-item (list new-manual-pts)))
                                        (setq new-s-item (append new-s-item (list val)))
                                      )
                                      (setq idx (1+ idx))
                                    )
                                    (setq s-item new-s-item)
                                  )
                                )
                              )
                            )
                            (setq new-support (append new-support (list s-item)))
                          )
                          (setq seg (subst (cons 'SUPPORT-LIST new-support) (assoc 'SUPPORT-LIST seg) seg))
                        )
                      )
                      (setq shifted-seg-list (append shifted-seg-list (list seg)))
                    )
                    (setq new-seg-list shifted-seg-list)
                    
                    ;; [추가] 글로벌 SUPPORT-LIST 변수도 동일하게 변위 보정 처리
                    (if *tsp-support-list*
                      (progn
                        (setq new-global-support nil)
                        (foreach s-item *tsp-support-list*
                          (if (wcmatch (car s-item) "버팀보*")
                            (progn
                              (setq s-manual-pts (if (> (length s-item) 8) (nth 8 s-item) nil))
                              (if s-manual-pts
                                (progn
                                  (setq new-manual-pts (mapcar '(lambda (pt) (list (+ (car pt) delta-x) (+ (cadr pt) delta-y) (caddr pt))) s-manual-pts))
                                  (setq new-s-item '())
                                  (setq idx 0)
                                  (foreach val s-item
                                    (if (= idx 8)
                                      (setq new-s-item (append new-s-item (list new-manual-pts)))
                                      (setq new-s-item (append new-s-item (list val)))
                                    )
                                    (setq idx (1+ idx))
                                  )
                                  (setq s-item new-s-item)
                                )
                              )
                            )
                          )
                          (setq new-global-support (append new-global-support (list s-item)))
                        )
                        (setq *tsp-support-list* new-global-support)
                      )
                    )
              
              ;; 수동으로 추가/삭제된 중간말뚝의 절대좌표도 새 위치에 맞게 변위(Shift) 일괄 적용
              (if *tsp-deleted-post-points*
                (setq *tsp-deleted-post-points* (mapcar '(lambda (pt) (list (+ (car pt) delta-x) (+ (cadr pt) delta-y) 0.0)) *tsp-deleted-post-points*)
                )
              )
              (if *tsp-added-post-points*
                (setq *tsp-added-post-points*
                  (mapcar '(lambda (rec) (cons (list (+ (car (car rec)) delta-x) (+ (cadr (car rec)) delta-y) 0.0) (cdr rec))) *tsp-added-post-points*)
                )
              )
              
              ;; 보정된 말뚝 데이터를 도면 딕셔너리에 즉각 업데이트하여 새 위치 기준으로 작도되게 함
              (vlax-ldata-put "TSP_DICT" "DELETED_POSTS" *tsp-deleted-post-points*)
              (vlax-ldata-put "TSP_DICT" "ADDED_POSTS" *tsp-added-post-points*)
            )
            (princ "\n[알림] 삽입점이 지정되지 않아 원래 위치에 생성합니다.")
          )
        )
      )
      
     ;; 전역 리스트 복원
      (setq *segment-list* new-seg-list)
      
      ;; 경계선 생성 및 방향 계산
      (setq new-boundary (tsp-rebuild-boundary))
      (setq new-orient (determine-boundary-orientation new-boundary))
      
      ;; 생성된 경계선의 레이어 생성 및 색상 강제 지정 로직
      (if (not (tblsearch "LAYER" "_경계선(Boundary)"))
        (entmake (list (cons 0 "LAYER") (cons 100 "AcDbSymbolTableRecord") (cons 100 "AcDbLayerTableRecord") (cons 2 "_경계선(Boundary)") (cons 70 0) (cons 62 4)))
      )
      (setq bnd-data (entget new-boundary))
      (setq bnd-data (subst (cons 8 "_경계선(Boundary)") (assoc 8 bnd-data) bnd-data))
      (if (assoc 62 bnd-data)
        (setq bnd-data (subst (cons 62 4) (assoc 62 bnd-data) bnd-data))
        (setq bnd-data (append bnd-data (list (cons 62 4))))
      )
      (entmod bnd-data)
      
      (vlax-ldata-put new-boundary "TSP_START_PT" (cdr (assoc 'V-START (nth 0 new-seg-list))))
      
      ;; 도면 딕셔너리에 즉시 세이브
      (tsp-save-project-data *tsp-current-project-name*)
      
      ;; 불러온 데이터로 백그라운드 평면도 강제 작도
      (tsp-redraw-realtime-plan new-boundary new-orient)
      
      ;; 합류(RUN)를 위한 전역 변수 세팅
      (setq *tsp-imported-ent* new-boundary)
      (setq *tsp-imported-orient* new-orient)
      (setq *is-imported-data* T)
      
      (alert (strcat "데이터 복원이 완료되었습니다.\n프로젝트명: " *tsp-current-project-name* "\n확인을 누르시면 즉시 [세그먼트 설정창]으로 진입합니다."))
    )
    (setq *is-imported-data* nil) ; 취소 시를 대비한 안전장치
  )
  *is-imported-data* ; T를 반환하여 메인 명령어가 RUN으로 넘어감
)


;;;;==========================================================================
;;;; defun tsp-select-project-for-load : 불러올 프로젝트를 DCL에서 선택 (도면 내부용)
;;;;==========================================================================
(defun tsp-select-project-for-load (/ dict proj-list dcl-id dcl-path dcl-file selected-proj idx item)
  (setq dict (dictsearch (namedobjdict) "TSP_DATA_DICT"))
  ;; 예외 처리: 도면에 딕셔너리가 아예 없는 경우
  (if (not dict)
    (progn (alert "현재 도면에 저장된 프로젝트 데이터가 없습니다.\n(저장된 이력이 없습니다.)") nil)
    (progn
      (setq proj-list nil)
      (foreach item dict
        (if (= (car item) 3)
          (setq proj-list (append proj-list (list (cdr item))))
        )
      )
      ;; 예외 처리: 딕셔너리는 있으나 내용물이 비어있는 경우
      (if (= (length proj-list) 0)
        (progn (alert "도면 내에 저장된 프로젝트가 없습니다.") nil)
        (progn
          (setq dcl-path (strcat (getvar "TEMPPREFIX") "tsp_load_dwg.dcl"))
          (setq dcl-file (open dcl-path "w"))
          (write-line "tsp_load_dwg_dlg : dialog { label = \"도면 내 프로젝트 불러오기\";" dcl-file)
          (write-line "  : list_box { key = \"proj_list\"; height = 10; width = 40; }" dcl-file)
          (write-line "  : row { : button { key = \"accept\"; label = \"불러오기(Load)\"; is_default = true; } : button { key = \"cancel\"; label = \"취소\"; is_cancel = true; } }" dcl-file)
          (write-line "}" dcl-file)
          (close dcl-file)

          (setq dcl-id (load_dialog dcl-path))
          (if (new_dialog "tsp_load_dwg_dlg" dcl-id)
            (progn
              (start_list "proj_list")
              (mapcar 'add_list proj-list)
              (end_list)
              (setq selected-proj nil)
              (action_tile "proj_list" "(setq idx (atoi $value))")
              (action_tile "accept" "(if idx (setq selected-proj (nth idx proj-list))) (done_dialog 1)")
              (action_tile "cancel" "(done_dialog 0)")
              (start_dialog)
              (unload_dialog dcl-id)
              selected-proj
            )
            (progn (alert "DCL 로드 실패") nil)
          )
        )
      )
    )
  )
)

;;;;==========================================================================
;;;; defun tsp-import-from-drawing : 도면 내부 딕셔너리에서 데이터를 읽어 복원
;;;;==========================================================================
(defun tsp-import-from-drawing (/ proj-name data-pack new-seg-list ins-opt ins-pt base-pt delta-x delta-y shifted-seg-list old-start old-end new-start new-end new-boundary new-orient bnd-data s-item s-manual-pts new-manual-pts new-s-item idx new-support old-support new-global-support seg val pt rec)
  (setq proj-name (tsp-select-project-for-load))
  (if proj-name
    (progn
      (setq data-pack (vlax-ldata-get "TSP_DATA_DICT" proj-name))
      (if (not data-pack)
        (progn (alert "선택한 프로젝트 데이터를 읽을 수 없습니다.") nil)
        (progn
          ;; 1. 전역 변수로 데이터 언패킹 (깊은 복사)
          (setq *tsp-current-project-name* proj-name)
          (setq new-seg-list (nth 0 data-pack))
          (setq *tsp-hpile-spec* (nth 1 data-pack))
          (setq *tsp-hpile-custom* (nth 2 data-pack))
          (setq *tsp-wale-spec* (nth 3 data-pack))
          (setq *tsp-wale-custom* (nth 4 data-pack))
          (setq *tsp-ctc* (nth 5 data-pack))
          (setq *tsp-timber-thickness* (nth 6 data-pack))
          (setq *tsp-max-excavation-depth* (nth 7 data-pack))
          (setq *tsp-embedment-depth* (nth 8 data-pack))
          (setq *tsp-soil-layers* (nth 9 data-pack))
          (setq *tsp-water-chk* (nth 10 data-pack))
          (setq *tsp-water-depth* (nth 11 data-pack))
          (setq *tsp-support-list* (tsp-sanitize-support-list (nth 12 data-pack)))
          (setq *tsp-scale-section* (nth 13 data-pack))
          (setq *tsp-scale-plan* (nth 14 data-pack))
          
          ;; 하위 버전 호환성 방어 로직 (15, 16 인덱스 존재 여부 파악)
          (if (> (length data-pack) 15)
            (progn
              (setq *tsp-deleted-post-points* (nth 15 data-pack))
              (setq *tsp-added-post-points* (nth 16 data-pack))
            )
            (progn
              (setq *tsp-deleted-post-points* '())
              (setq *tsp-added-post-points* '())
            )
          )

          ;; 2. 삽입점 지정 및 좌표 보정 방식 선택
          (initget "Origin New")
          (setq ins-opt (getkword "\n불러올 도면의 삽입 방식을 선택하세요 [원래위치(O)/새위치(N)] <N>: "))
          (if (not ins-opt) (setq ins-opt "New"))
          
          (if (= ins-opt "New")
            (progn
              (setq ins-pt (getpoint "\n1번 세그먼트의 시작점이 될 위치를 클릭하세요: "))
              (if ins-pt
                (progn
                  (setq ins-pt (trans ins-pt 1 0)) ;; WCS 변환
                  (setq base-pt (cdr (assoc 'V-START (nth 0 new-seg-list))))
                  (setq delta-x (- (car ins-pt) (car base-pt)))
                  (setq delta-y (- (cadr ins-pt) (cadr base-pt)))
                  
                  ;; 2-1. 세그먼트 양 끝단 좌표 및 수동 버팀보 Shift 일괄 적용
                  (setq shifted-seg-list nil)
                  (foreach seg new-seg-list
                    (setq old-start (cdr (assoc 'V-START seg)))
                    (setq old-end (cdr (assoc 'V-END seg)))
                    (setq new-start (list (+ (car old-start) delta-x) (+ (cadr old-start) delta-y) (if (caddr old-start) (caddr old-start) 0.0)))
                    (setq new-end (list (+ (car old-end) delta-x) (+ (cadr old-end) delta-y) (if (caddr old-end) (caddr old-end) 0.0)))
                    
                    (setq seg (subst (cons 'V-START new-start) (assoc 'V-START seg) seg))
                    (setq seg (subst (cons 'V-END new-end) (assoc 'V-END seg) seg))
                    
                    ;; 세그먼트 내 버팀보 좌표 보정
                    (setq old-support (tsp-sanitize-support-list (cdr (assoc 'SUPPORT-LIST seg))))
                    (if old-support
                      (progn
                        (setq new-support nil)
                        (foreach s-item old-support
                          (if (wcmatch (car s-item) "버팀보*")
                            (progn
                              (setq s-manual-pts (if (> (length s-item) 8) (nth 8 s-item) nil))
                              (if s-manual-pts
                                (progn
                                  (setq new-manual-pts (mapcar '(lambda (pt) (list (+ (car pt) delta-x) (+ (cadr pt) delta-y) (if (caddr pt) (caddr pt) 0.0))) s-manual-pts))
                                  (setq new-s-item '())
                                  (setq idx 0)
                                  (foreach val s-item
                                    (if (= idx 8)
                                      (setq new-s-item (append new-s-item (list new-manual-pts)))
                                      (setq new-s-item (append new-s-item (list val)))
                                    )
                                    (setq idx (1+ idx))
                                  )
                                  (setq s-item new-s-item)
                                )
                              )
                            )
                          )
                          (setq new-support (append new-support (list s-item)))
                        )
                        (setq seg (subst (cons 'SUPPORT-LIST new-support) (assoc 'SUPPORT-LIST seg) seg))
                      )
                    )
                    (setq shifted-seg-list (append shifted-seg-list (list seg)))
                  )
                  (setq new-seg-list shifted-seg-list)
                  
                  ;; 2-2. 글로벌 버팀보 좌표 Shift 적용
                  (if *tsp-support-list*
                    (progn
                      (setq new-global-support nil)
                      (foreach s-item *tsp-support-list*
                        (if (wcmatch (car s-item) "버팀보*")
                          (progn
                            (setq s-manual-pts (if (> (length s-item) 8) (nth 8 s-item) nil))
                            (if s-manual-pts
                              (progn
                                (setq new-manual-pts (mapcar '(lambda (pt) (list (+ (car pt) delta-x) (+ (cadr pt) delta-y) (if (caddr pt) (caddr pt) 0.0))) s-manual-pts))
                                (setq new-s-item '())
                                (setq idx 0)
                                (foreach val s-item
                                  (if (= idx 8)
                                    (setq new-s-item (append new-s-item (list new-manual-pts)))
                                    (setq new-s-item (append new-s-item (list val)))
                                  )
                                  (setq idx (1+ idx))
                                )
                                (setq s-item new-s-item)
                              )
                            )
                          )
                        )
                        (setq new-global-support (append new-global-support (list s-item)))
                      )
                      (setq *tsp-support-list* new-global-support)
                    )
                  )
                  
                  ;; 2-3. 삭제/추가된 말뚝 좌표 Shift 일괄 보정
                  (if *tsp-deleted-post-points*
                    (setq *tsp-deleted-post-points* (mapcar '(lambda (pt) (list (+ (car pt) delta-x) (+ (cadr pt) delta-y) 0.0)) *tsp-deleted-post-points*))
                  )
                  (if *tsp-added-post-points*
                    (setq *tsp-added-post-points* (mapcar '(lambda (rec) (cons (list (+ (car (car rec)) delta-x) (+ (cadr (car rec)) delta-y) 0.0) (cdr rec))) *tsp-added-post-points*))
                  )
                )
                (princ "\n[알림] 삽입점이 지정되지 않아 기존 절대좌표 원래 위치에 생성합니다.")
              )
            )
          )

          ;; 3. 전역 리스트 복원 및 딕셔너리 안전장치 저장
          (setq *segment-list* new-seg-list)
          (vlax-ldata-put "TSP_DICT" "DELETED_POSTS" *tsp-deleted-post-points*)
          (vlax-ldata-put "TSP_DICT" "ADDED_POSTS" *tsp-added-post-points*)
          
          ;; 4. 폴리라인 재작도 (백그라운드 복원)
          (setq new-boundary (tsp-rebuild-boundary))
          (setq new-orient (determine-boundary-orientation new-boundary))
          
          ;; 레이어 생성 및 색상 강제 지정
          (if (not (tblsearch "LAYER" "_경계선(Boundary)"))
            (entmake (list (cons 0 "LAYER") (cons 100 "AcDbSymbolTableRecord") (cons 100 "AcDbLayerTableRecord") (cons 2 "_경계선(Boundary)") (cons 70 0) (cons 62 4)))
          )
          (setq bnd-data (entget new-boundary))
          (setq bnd-data (subst (cons 8 "_경계선(Boundary)") (assoc 8 bnd-data) bnd-data))
          (if (assoc 62 bnd-data)
            (setq bnd-data (subst (cons 62 4) (assoc 62 bnd-data) bnd-data))
            (setq bnd-data (append bnd-data (list (cons 62 4))))
          )
          (entmod bnd-data)
          
          (vlax-ldata-put new-boundary "TSP_START_PT" (cdr (assoc 'V-START (nth 0 new-seg-list))))
          
          ;; RUN 상태 진입을 위한 플래그 처리
          (setq *tsp-imported-ent* new-boundary)
          (setq *tsp-imported-orient* new-orient)
          (setq *is-imported-data* T)
          
          (alert (strcat "프로젝트 [" proj-name "] 복원이 완료되었습니다.\n확인을 누르시면 즉시 [세그먼트 설정창]으로 진입합니다."))
        )
      )
    )
    (setq *is-imported-data* nil) ; 취소 시 안전하게 nil 반환
  )
  *is-imported-data* ; T를 반환하면 메인 메뉴에서 RUN 상태로 전환됨
)


;;;;==========================================================================
;;; Command: TSP
;;; Description: 가시설 평면/단면 통합 작도 메인 명령어 (Export/Import 기능 통합)
;;;;==========================================================================
(defun C:TSP (/ old-layer old-err dcl-path boundary-ent boundary-orient step status sel loop-program loop-draw seg-data section-draw-flag opt soil-src valid-sources idx s-data src-num src-idx perform-draw input-valid default-src save-chk loop-save saved-list user-start-pt vertices poly-orient start-idx dist-start dist-end saved-start-pt use-saved last-ent handle group-name dict group-exists has-brace-y ans g-brace i new-list missing-brace-list b-data curr-len prev-idx prev-data prev-len limits new-brace abort-draw rem-count res ans2 mseg midx check-data draw-seg draw-cor proceed-draw choice-res ans-cor brace-res selected-idx dcl-id user-choice)
  (setvar "cmdecho" 0)
  
  (setq old-layer (getvar "CLAYER"))
  
  (setq old-err *error*)
  (defun *error* (msg)
    (if old-layer (setvar "CLAYER" old-layer))
    (setvar "cmdecho" 1)
    (if (and msg (not (wcmatch (strcase msg) "*BREAK*,*CANCEL*,*QUIT*")))
      (princ (strcat "\n오류 발생: " msg))
      (princ "\n명령이 취소되었습니다.")
    )
    (setq *error* old-err)
    (princ)
  )

  (princ "\n========================================")
  (princ "\nTSP - Temporary Structure Plan")
  (princ "\n========================================\n")
  (setq *tsp-wall-type* "HPILE")
  (setq dcl-path (create-tsp-dcl))
  
  ;; 사용자의 선택에 따른 분기 (가상 상태 머신 적용)
  (setq *is-imported-data* nil)
  (setq next-step "MAIN_MENU") ; 시작 상태를 메인 메뉴로 설정
  
  (while next-step
    (cond
      ((= next-step "MAIN_MENU")
        ;; [메인 메뉴 호출 로직] - 상태 머신 내부로 이동하여 루프 가능하도록 수정
        (setq dcl-id (load_dialog dcl-path))
        (if (not (new_dialog "tsp_main_menu" dcl-id))
          (progn (alert "메인 메뉴 DCL 로드 실패") (exit))
        )
        (setq user-choice "CANCEL")
        (action_tile "btn_run" "(setq user-choice \"RUN\") (done_dialog 1)")
        (action_tile "btn_export" "(setq user-choice \"EXPORT\") (done_dialog 2)")
        (action_tile "btn_import" "(setq user-choice \"IMPORT\") (done_dialog 3)")
        (action_tile "btn_load_dwg" "(setq user-choice \"LOAD_DWG\") (done_dialog 4)")
        (action_tile "cancel" "(setq user-choice \"CANCEL\") (done_dialog 0)")
        (start_dialog)
        (unload_dialog dcl-id)
        (setq next-step user-choice)
      )
      ((= next-step "EXPORT")
       (tsp-export-to-csv)
       (setq next-step "MAIN_MENU") 
      )
      ((= next-step "IMPORT")
       (if (tsp-import-from-csv)
         (setq next-step "RUN") 
         (setq next-step "MAIN_MENU") 
       )
      )
      ((= next-step "LOAD_DWG")
       (if (tsp-import-from-drawing)
         (setq next-step "RUN") 
         (setq next-step "MAIN_MENU") 
       )
      )
      ((= next-step "RUN")
        (setq next-step nil)
      (setq step 0)
      (setq loop-program T)
      (setq *tsp-data-dirty* nil)
      (setq *tsp-project-modified* nil)
      (setq *tsp-realtime-entities* '())
      
      (setq status (scale-dialog-callback dcl-path))
      
      (cond
        ((= status 0) ; 취소
          (setq loop-program nil)
        )
        ((= status 4) ; 이전(Back)
          (setq loop-program nil)
          (setq next-step "MAIN_MENU") ; 메인 메뉴로 돌아가도록 루프 상태 변경
        )
        (t ; 확인(1)
          (setq loop-program T)
        )
      )
      
      (setq *tsp-data-dirty* nil)
      (if loop-program
        (progn
          (if *is-imported-data*
            (progn
              (setq boundary-ent *tsp-imported-ent*)
              (princ "\n[시스템] 불러온 데이터를 기반으로 도면 작업을 이어서 진행합니다.")
            )
            (progn
              (setq boundary-ent nil)
              (while (not boundary-ent)
                (initget "Exit")
                (setq sel (entsel "\n'STEP 1' 전체 구간의 경계선(Polyline)을 선택하세요 [종료(Exit)]: "))
                (cond
                  ((= sel "Exit") (princ "\n명령을 종료합니다.") (setq boundary-ent "CANCEL"))
                  ((/= sel nil) (setq boundary-ent (car sel)))
                  ((= sel nil) (princ "\n선택되지 않았습니다. 다시 선택해주세요."))
                  ((= (getvar "ERRNO") 7) (princ "\n빈 공간입니다. 다시 선택하세요.") (setvar "ERRNO" 0))
                  (t (princ "\n선택 취소됨.") (setq boundary-ent "CANCEL"))
                )
              )
            )
          )
          (if (and boundary-ent (/= boundary-ent "CANCEL"))
            (progn
              (if *is-imported-data*
                (progn
                  (setq boundary-orient *tsp-imported-orient*)
                  (setq *tsp-boundary-ent* boundary-ent)
                  (setq *tsp-boundary-orient* boundary-orient)
                )
                (progn
                  (tsp-fix-mirrored-polyline boundary-ent)
                  (setq boundary-orient (determine-boundary-orientation boundary-ent))
                  (setq *tsp-boundary-ent* boundary-ent)
                  (setq *tsp-boundary-orient* boundary-orient)
                )
              )
              
              (if boundary-orient
                (progn
                  (setq vertices (extract-vertices boundary-ent))
                  (tsp-zoom-to-right-half vertices)
                  
                  (if (not *is-imported-data*)
                    (progn
                      (setq saved-start-pt (vlax-ldata-get boundary-ent "TSP_START_PT"))
                      (setq saved-start-idx (vlax-ldata-get boundary-ent "TSP_START_IDX"))
                      (setq user-start-pt nil)
                      (setq use-saved nil)
                      
                      ;; [추가] 복사된 객체 감지: 저장된 절대좌표가 현재 객체에서 멀리 떨어져 있다면 복사본으로 판별
                      (setq is-copied-ent nil)
                      (if saved-start-pt
                        (progn
                          (setq temp-idx (tsp-get-closest-vertex-index vertices saved-start-pt))
                          (if (> (distance (nth temp-idx vertices) saved-start-pt) 10.0)
                            (setq is-copied-ent T)
                          )
                        )
                      )
                      
                      (if saved-start-pt
                        (if (and is-copied-ent (not saved-start-idx))
                          (progn
                            ;; 인덱스 데이터가 없는 구버전 도면을 복사했을 경우의 안전장치
                            (princ "\n[시스템] 복사된 경계선이 감지되었습니다. 이전 절대좌표 방식으로는 시작점이 틀어지므로 새로 지정해야 합니다.")
                            (setq use-saved nil)
                          )
                          (progn
                            (initget "Yes No")
                            (if (= (getkword "\n 이전에 사용된 시작점이 있습니다. 그대로 사용하시겠습니까? [Yes(Y)/No(N)] <Y>: ") "No")
                              (setq use-saved nil)
                              (setq use-saved T)
                            )
                          )
                        )
                      )
                      
                      (if use-saved
                        (progn
                          (setq user-start-pt saved-start-pt)
                          (if (and is-copied-ent saved-start-idx)
                            (princ "\n[시스템] 복사된 객체입니다. 저장된 기하학적 인덱스(Index)를 사용하여 시작점 순서를 완벽히 유지합니다.")
                          )
                        )
                        (progn
                          (reset-globals-to-defaults)
                          (setq *segment-list* nil)
                          (setq *tsp-current-project-name* "")
                          (princ "\n[시스템] 새로운 시작점이 지정되어 기존 세그먼트 설정 및 프로젝트 이름이 초기화됩니다.")
                          (setq user-start-pt (getpoint "\n세그먼트 시작점(No.1)이 될 위치를 클릭하세요: "))
                          (if user-start-pt
                            (progn
                              (setq user-start-pt (trans user-start-pt 1 0))
                              (vlax-ldata-put boundary-ent "TSP_START_PT" user-start-pt)
                            )
                          )
                        )
                      )
                      
                      (if (is-closed-polyline boundary-ent)
                        (progn
                           (setq poly-orient (get-polygon-orientation vertices))
                           (if (= poly-orient 1)
                             (progn
                               (setq vertices (reverse vertices))
                               (setq boundary-orient (- boundary-orient))
                               (setq *tsp-boundary-orient* boundary-orient)
                             )
                           )
                           (if user-start-pt
                             (progn
                               ;; 복사본이면서 인덱스가 존재하면 절대좌표 연산을 무시하고 인덱스를 강제 적용
                               (if (and use-saved is-copied-ent saved-start-idx)
                                 (setq start-idx saved-start-idx)
                                 (setq start-idx (tsp-get-closest-vertex-index vertices user-start-pt))
                               )
                               (setq vertices (tsp-shift-vertex-list vertices start-idx))
                               ;; 다음 복사를 완벽히 대비해 인덱스 번호를 무조건 갱신 및 저장
                               (vlax-ldata-put boundary-ent "TSP_START_IDX" start-idx)
                             )
                           )
                        )
                        (progn
                           (if user-start-pt
                             (progn
                               (setq dist-start (distance (car vertices) user-start-pt))
                               (setq dist-end (distance (last vertices) user-start-pt))
                               (if (< dist-end dist-start)
                                 (progn
                                   (setq vertices (reverse vertices))
                                   (setq boundary-orient (- boundary-orient))
                                   (setq *tsp-boundary-orient* boundary-orient)
                                 )
                               )
                             )
                           )
                        )
                      )
                      (init-segment-data boundary-ent boundary-orient vertices)
                    )
                  )
                  (setq handle (tsp-get-entity-handle boundary-ent))
                  (setq group-name (strcat "TSP_GRP_" handle))
                  (setq dict (dictsearch (namedobjdict) "ACAD_GROUP"))
                  (setq group-exists (if (and dict (dictsearch (cdr (assoc -1 dict)) group-name)) T nil))
                  (if (not group-exists)
                    (progn
                      (setq last-ent (entlast))
                      (draw-segment-numbers boundary-ent boundary-orient vertices)
                      (tsp-group-last-entities last-ent boundary-ent)
                    )
                    (princ "\n[알림] 기존 평면도를 유지한 상태로 설정창에 진입합니다.")
                  )
                  (tsp-redraw-realtime-plan boundary-ent boundary-orient)
                  (setq loop-draw T)
                  (while loop-draw
                    (setq status (manager-dialog-callback dcl-path))
                    (cond
                      ((= status 0)
                        (setq loop-draw nil)
                        (if (or *tsp-data-dirty* *tsp-project-modified*)
                          (progn
                            (initget "Yes No")
                            (setq save-chk (getkword (strcat "\n변경된 내용을 저장하시겠습니까? (프로젝트: " *tsp-current-project-name* ") [Yes(Y)/No(N)] <Y>: ")))
                            (if (null save-chk) (setq save-chk "Yes"))
                            (if (= save-chk "Yes")
                              (tsp-save-project-data *tsp-current-project-name*)
                              (princ "\n[알림] 저장하지 않고 종료합니다.")
                            )
                          )
                          (princ "\n[알림] 변경된 내용이 없어 종료합니다.")
                        )
                        (princ "\nTSP 명령을 종료합니다.")
                      )
                      ((= status 5)
                       (setq check-data (nth selected-idx *segment-list*))
                       (setq b-data (cdr (assoc 'CORNER-BRACE check-data)))
                       (setq draw-seg T draw-cor nil)
                       (setq proceed-draw T)
                       (if (and b-data (= (car b-data) "Y"))
                         (progn
                           (setq choice-res (section-choice-dialog-callback dcl-path))
                           (if choice-res
                             (progn
                               (setq draw-seg (car choice-res) draw-cor (cadr choice-res))
                               (if draw-cor
                                 (progn
                                   (if (null (cadr b-data))
                                     (progn
                                       (initget "Input Skip Return")
                                       (setq ans-cor (getkword "\n선택한 모서리에 사보강재(Corner Strut) 정보가 없습니다. 작업선택 [입력(Input)/생략(Skip)/되돌리기(Return)] <Input>: "))
                                       (if (null ans-cor) (setq ans-cor "Input"))
                                       (cond
                                         ((= ans-cor "Input")
                                          (setq limits (tsp-calculate-brace-limit selected-idx))
                                          (setq brace-res (brace-dialog-callback dcl-path check-data limits 0))
                                          (if (and (listp brace-res) (or (= (car brace-res) "COMP") (= (car brace-res) "NEXT")))
                                            (progn
                                              (setq new-brace (cadr brace-res))
                                              (setq check-data (subst (cons 'CORNER-BRACE new-brace) (assoc 'CORNER-BRACE check-data) check-data))
                                              (setq check-data (subst (cons 'UPGRADE-WALE (caddr brace-res)) (assoc 'UPGRADE-WALE check-data) check-data))
                                              (setq *segment-list* (update-list-item *segment-list* selected-idx check-data))
                                              (setq b-data new-brace)
                                              (if (and new-brace (cadr new-brace) (> (length (cadr new-brace)) 0))
                                                (alert "모서리 단면도 작도는 아직 작업중입니다.")
                                                (princ "\n사보강재(Corner Strut) 정보가 입력되지 않았습니다.")
                                              )
                                            )
                                            (princ "\n입력이 취소되었습니다.")
                                          )
                                         )
                                         ((= ans-cor "Skip")
                                          (princ "\n모서리 단면도 생성을 생략합니다.")
                                         )
                                         ((= ans-cor "Return")
                                          (setq proceed-draw nil draw-seg nil)
                                         )
                                       )
                                     )
                                     (alert "모서리 단면도 작도는 아직 작업중입니다.")
                                   )
                                 )
                               )
                             )
                             (setq proceed-draw nil draw-seg nil)
                           )
                         )
                       )
                       (if (and proceed-draw draw-seg)
                         (progn
                           (setq perform-draw T)
                           (if (or (not *tsp-target-draw-flag*) (null *tsp-soil-layers*) (= *tsp-soil-layers* '()))
                             (progn
                               (initget "Input Copy Skip Return")
                               (setq opt (getkword "\n선택한 세그먼트에 지반 정보가 없거나 '단면생성 N'입니다. 작업 선택 [입력(Input)/복사(Copy)/생략(Skip)/되돌리기(Return)] <Skip>: "))
                               (cond
                                 ((= opt "Input") (if (= (soil-dialog-callback dcl-path) 1) (princ "\n지반 정보 입력 완료.") (progn (princ "\n입력이 취소되었습니다.") (setq perform-draw nil))))
                                 ((= opt "Copy")
                                  (setq valid-sources '() idx 0)
                                  (foreach seg *segment-list* (setq s-data (cdr (assoc 'SOIL-DATA seg))) (if (and s-data (/= s-data '())) (setq valid-sources (append valid-sources (list (1+ idx))))) (setq idx (1+ idx)))
                                  (if valid-sources
                                    (progn
                                      (princ (strcat "\n복사 가능한 세그먼트 번호: " (vl-princ-to-string valid-sources)))
                                      (setq input-valid nil default-src (car valid-sources))
                                      (while (not input-valid)
                                        (setq src-num (getint (strcat "\n지반 정보를 가져올 세그먼트 번호를 입력하세요 [기본값: " (itoa default-src) "]: ")))
                                        (if (null src-num) (setq src-num default-src))
                                        (if (vl-position src-num valid-sources)
                                          (progn (setq input-valid T src-idx (1- src-num)) (setq *tsp-soil-layers* (cdr (assoc 'SOIL-DATA (nth src-idx *segment-list*)))) (princ (strcat "\n" (itoa src-num) "번 세그먼트의 지반 정보를 적용했습니다.")))
                                          (princ "\n잘못된 번호입니다.")
                                        )
                                      )
                                    )
                                    (progn (alert "지반 정보가 입력된 세그먼트가 하나도 없습니다.") (setq perform-draw nil))
                                  )
                                 )
                                 ((= opt "Return") (setq perform-draw nil))
                                 (t (princ "\n지반 정보 없이 구조물 단면만 그립니다."))
                               )
                             )
                           )
                           (if perform-draw
                             (progn
                               (if (draw-section-ground-line dcl-path selected-idx)
                                 (princ "\n단면도 작도 완료.")
                                 (progn
                                   (princ "\n단면도 작도 취소됨.")
                                   (setq proceed-draw nil)
                                 )
                               )
                             )
                           )
                         )
                       )
                       (if proceed-draw
                         (progn
                           (initget "Yes No")
                           (setq choice-res (vl-catch-all-apply 'getkword (list "\n설정창으로 돌아가시겠습니까? [Yes(Y)/No(N)] <Y>: ")))
                           (if (vl-catch-all-error-p choice-res)
                             (setq loop-draw nil)
                             (if (= choice-res "No") (setq loop-draw nil))
                           )
                         )
                       )
                      )
                      ((= status 6)
                       (setq abort-draw nil)
                       (setq missing-brace-list '())
                       (setq i 0)
                       (while (< i (length *segment-list*))
                         (setq seg-data (nth i *segment-list*))
                         (setq b-data (cdr (assoc 'CORNER-BRACE seg-data)))
                         (if (and b-data (= (car b-data) "Y") (null (cadr b-data)))
                           (setq missing-brace-list (append missing-brace-list (list i)))
                         )
                         (setq i (1+ i))
                       )
                       (if (> (length missing-brace-list) 0)
                         (progn
                           (initget "Yes No")
                           (setq ans (getkword (strcat "\n사보강재(Corner Strut) 설정이 누락된 모서리가 " (itoa (length missing-brace-list)) "곳 있습니다. 추가하시겠습니까? [Yes(Y)/No(N)] <Y>: ")))
                           (if (or (null ans) (= ans "Yes"))
                             (progn
                               (while (and (> (length missing-brace-list) 0) (not abort-draw))
                                 (setq idx (car missing-brace-list))
                                 (setq missing-brace-list (cdr missing-brace-list))
                                 (setq seg-data (nth idx *segment-list*))
                                 (setq limits (tsp-calculate-brace-limit idx))
                                 (setq rem-count (1+ (length missing-brace-list)))
                                 (setq res (brace-dialog-callback dcl-path seg-data limits rem-count))
                                 (cond
                                   ((and (listp res) (= (car res) "NEXT"))
                                    (setq new-brace (cadr res))
                                    (if (and new-brace (cadr new-brace) (> (length (cadr new-brace)) 0))
                                      (progn
                                        (setq seg-data (subst (cons 'CORNER-BRACE new-brace) (assoc 'CORNER-BRACE seg-data) seg-data))
                                        (setq seg-data (subst (cons 'UPGRADE-WALE (caddr res)) (assoc 'UPGRADE-WALE seg-data) seg-data))
                                        (setq *segment-list* (update-list-item *segment-list* idx seg-data))
                                      )
                                      (progn
                                        (princ (strcat "\n[" (itoa (cdr (assoc 'ID seg-data))) "번 모서리] 데이터가 비어있어 순서를 맨 뒤로 미룹니다."))
                                        (setq missing-brace-list (append missing-brace-list (list idx)))
                                      )
                                    )
                                   )
                                   ((and (listp res) (= (car res) "COMP"))
                                    (setq new-brace (cadr res))
                                    (if (and new-brace (cadr new-brace) (> (length (cadr new-brace)) 0))
                                      (progn
                                        (setq seg-data (subst (cons 'CORNER-BRACE new-brace) (assoc 'CORNER-BRACE seg-data) seg-data))
                                        (setq seg-data (subst (cons 'UPGRADE-WALE (caddr res)) (assoc 'UPGRADE-WALE seg-data) seg-data))
                                        (setq *segment-list* (update-list-item *segment-list* idx seg-data))
                                      )
                                      (progn
                                        (princ (strcat "\n[" (itoa (cdr (assoc 'ID seg-data))) "번 모서리] 데이터가 비어있습니다. 해당 사보강재(Corner Strut) 설정을 건너뜁니다."))
                                        (setq seg-data (subst (cons 'CORNER-BRACE (list "N" nil)) (assoc 'CORNER-BRACE seg-data) seg-data))
                                        (setq *segment-list* (update-list-item *segment-list* idx seg-data))
                                      )
                                    )
                                    (if (> (length missing-brace-list) 0)
                                      (progn
                                        (initget "Yes No")
                                        (setq ans2 (getkword (strcat "\n아직 사보강재(Corner Strut)가 입력되지 않은 세그먼트가 " (itoa (length missing-brace-list)) "곳 남았습니다. 이대로 설정을 완전히 종료하시겠습니까? (Yes:완료 / No:마저입력) [Yes/No] <No>: ")))
                                        (if (= ans2 "Yes")
                                          (progn
                                            (foreach midx missing-brace-list
                                              (setq mseg (nth midx *segment-list*))
                                              (setq mseg (subst (cons 'CORNER-BRACE (list "N" nil)) (assoc 'CORNER-BRACE mseg) mseg))
                                              (setq *segment-list* (update-list-item *segment-list* midx mseg))
                                            )
                                            (setq missing-brace-list '())
                                          )
                                        )
                                      )
                                    )
                                   )
                                   (t
                                     (princ "\n입력이 취소되었습니다. 평면도 생성을 중단합니다.")
                                     (setq abort-draw T)
                                   )
                                 )
                               )
                             )
                             (progn
                               (princ "\n사보강재(Corner Strut) 추가를 건너뜁니다. 해당 모서리는 사보강재(Corner Strut) 없이 작도됩니다.")
                               (foreach idx missing-brace-list
                                 (setq seg-data (nth idx *segment-list*))
                                 (setq seg-data (subst (cons 'CORNER-BRACE (list "N" nil)) (assoc 'CORNER-BRACE seg-data) seg-data))
                                 (setq *segment-list* (update-list-item *segment-list* idx seg-data))
                               )
                             )
                           )
                         )
                       )
                       (if (not abort-draw)
                         (progn
                           (princ "\n모든 데이터가 확인되었습니다. 최종 평면도를 갱신합니다.")
                           (if (and *tsp-boundary-ent* *tsp-boundary-orient*)
                             (tsp-redraw-realtime-plan *tsp-boundary-ent* *tsp-boundary-orient*)
                           )
                         )
                       )
                       (if (not abort-draw)
                         (if *tsp-cancel-flag*
                           (setq *tsp-cancel-flag* nil)
                           (progn
                             (initget "Yes No")
                             (setq user-ans (vl-catch-all-apply 'getkword (list "\n설정창으로 다시 돌아가시겠습니까? [Yes(Y)/No(N)] <Y>: ")))
                             (if (vl-catch-all-error-p user-ans)
                               (setq loop-draw nil)
                               (if (= user-ans "No") (setq loop-draw nil))
                             )
                           )
                         )
                       )
                      )
                    ) ;; end cond
                  ) ;; end while loop-draw
                ) ;; end progn (if boundary-orient)
              ) ;; end if boundary-orient
            ) ;; end progn (if boundary-ent)
          ) ;; end if boundary-ent
        ) ;; end progn (if loop-program)
      ) ;; end if loop-program
      ;; ----- 도면 작업 루프 원본 끝 -----
    )
    ((= next-step "CANCEL")
       (princ "\nTSP 명령어가 취소되었습니다.")
       (setq next-step nil)
      )
    )
  )
  
  (if old-layer (setvar "CLAYER" old-layer))
  (setq *error* old-err)
  
  (setvar "cmdecho" 1)
  (princ)
)


;;;;==========================================================================
;;;; defun tsp-extract-number-only : 텍스트에서 숫자와 소수점('.')만 추출
;;;;==========================================================================
(defun tsp-extract-number-only (str / i char res)
  (setq res "")
  (setq i 1)
  (while (<= i (strlen str))
    (setq char (substr str i 1))
    (if (or (and (>= (ascii char) 48) (<= (ascii char) 57))
            (= (ascii char) 46))
      (setq res (strcat res char))
    )
    (setq i (1+ i))
  )
  (if (= res "") "0.0" res)
)

;;;;==========================================================================
;;;; defun tsp-get-nvalue-from-drawing : 도면에서 텍스트를 드래그하여 N치 추출
;;;;==========================================================================
(defun tsp-get-nvalue-from-drawing (/ ss i ent ent-data txt-str pt-x pt-y txt-h txt-list row-list current-row prev-y new-n-values depth-str depth-val n-text)
  (princ "\n[N치 자동입력] 깊이와 N치 텍스트들을 드래그하여 선택하세요: ")
  (setq ss (ssget '((0 . "TEXT"))))
  (if (not ss)
    (progn (princ "\n선택된 텍스트가 없습니다.") nil)
    (progn
      (if (= (rem (sslength ss) 2) 1)
        (progn
          (alert "선택된 텍스트의 총 개수가 홀수입니다.\n깊이와 N치가 짝수 개로 맞는지 확인하고 다시 선택해주세요.")
          nil
        )
        (progn
          (setq txt-list '() i 0)
          (while (< i (sslength ss))
            (setq ent (ssname ss i))
            (setq ent-data (entget ent))
            (setq txt-str (cdr (assoc 1 ent-data)))
            (setq txt-h (cdr (assoc 40 ent-data)))
            (setq pt-x (car (cdr (assoc 10 ent-data))))
            (setq pt-y (cadr (cdr (assoc 10 ent-data))))
            (setq txt-list (append txt-list (list (list pt-y pt-x txt-str txt-h))))
            (setq i (1+ i))
          )
          (setq txt-list (vl-sort txt-list (function (lambda (a b) (> (car a) (car b))))))
          (setq row-list '() current-row '() prev-y (car (nth 0 txt-list)))
          (foreach item txt-list
            (setq pt-y (nth 0 item) txt-h (nth 3 item))
            (if (<= (abs (- prev-y pt-y)) (* txt-h 0.5))
              (setq current-row (append current-row (list item)))
              (progn
                (setq row-list (append row-list (list current-row)))
                (setq current-row (list item) prev-y pt-y)
              )
            )
          )
          (if current-row (setq row-list (append row-list (list current-row))))
          (setq new-n-values '())
          (foreach row row-list
            (if (= (length row) 2)
              (progn
                (setq row (vl-sort row (function (lambda (a b) (< (cadr a) (cadr b))))))
                (setq depth-str (tsp-extract-number-only (nth 2 (nth 0 row))))
                (setq depth-val (atof depth-str))
                (setq n-text (nth 2 (nth 1 row)))
                (setq new-n-values (append new-n-values (list (list depth-val n-text))))
              )
            )
          )
          (if (> (length new-n-values) 0)
            (progn
              (alert (strcat "총 " (itoa (length new-n-values)) "쌍의 N치 데이터가 성공적으로 추가되었습니다."))
              new-n-values
            )
            (progn
              (alert "유효한 N치 데이터를 찾을 수 없습니다.\n행의 짝(깊이, N치)이 맞게 선택되었는지 확인해주세요.")
              nil
            )
          )
        )
      )
    )
  )
)

(princ "\nTSP.lsp 로드 완료!")
(princ "\n  명령어: TSP")
(princ)



;;;;==========================================================================
;;;; 디버깅 전용 실시간 파일 로그 출력 함수
;;;;==========================================================================
(defun tsp-log (msg / f path)
  (setq path "C:\\tsp_debug.log")
  (setq f (open path "a"))
  (if f
    (progn
      (write-line (strcat "[" (rtos (getvar "CDATE") 2 6) "] " msg) f)
      (close f)
    )
  )
  (princ (strcat "\n" msg))
  (princ)
)
